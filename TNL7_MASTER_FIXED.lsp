;;; TNL7_MASTER.lsp
;;; Standalone AutoLISP reconstruction generated from verified TNL7 source data.
;;; This file does not read TNL7.dxf at runtime.

(defun tnl7-ensure-data ()
  (unless (boundp '*tnl7-contour*)
    (setq *tnl7-origin-x* -226.3064263061785)
    (setq *tnl7-origin-y* 121.2980488058441)
    (setq *tnl7-contour* (list
  ( "LWPOLYLINE" "CACEM - LINEE SCHEDA" ((vertices . (((x . -213.478813809322) (y . 121.493216363377)))) (bulges . ()) (closed . T)))
  ("LINE" "CACEM - LINEE SCHEDA" ((start . ((x . -223.206239565008) (y . 125.552677069509))) (end . ((x . -223.206234340295) (y . 136.787270026142)))))
  ("LINE" "CACEM - LINEE SCHEDA" ((start . ((x . -223.839481123387) (y . 125.552677069509))) (end . ((x . -223.839475898667) (y . 136.787270026142)))))
  ("LINE" "CACEM - LINEE SCHEDA" ((start . ((x . -224.472722449476) (y . 125.552677069509))) (end . ((x . -224.472717224762) (y . 136.787270026142)))))
  ("LINE" "CACEM - LINEE SCHEDA" ((start . ((x . -224.959831269053) (y . 125.552677069509))) (end . ((x . -224.95982604434) (y . 136.787270026142)))))
  ("LINE" "CACEM - LINEE SCHEDA" ((start . ((x . -225.57390398665) (y . 125.552677069509))) (end . ((x . -225.573898878508) (y . 136.787270026142)))))
  ("LINE" "CACEM - LINEE SCHEDA" ((start . ((x . -226.146345044587) (y . 135.886119267359))) (end . ((x . -221.160377240042) (y . 135.886119267359)))))
  ("LINE" "CACEM - LINEE SCHEDA" ((start . ((x . -226.146339110414) (y . 136.446294409881))) (end . ((x . -221.160377325208) (y . 136.446294409881)))))
  ("LINE" "CACEM - LINEE SCHEDA" ((start . ((x . -226.146338994281) (y . 136.787270955223))) (end . ((x . -221.160377377051) (y . 136.787270955223)))))
  ("LINE" "CACEM - LINEE SCHEDA" ((start . ((x . -226.146351007793) (y . 135.358620037232))) (end . ((x . -221.160377149913) (y . 135.358620037232)))))
  ("LINE" "CACEM - LINEE SCHEDA" ((start . ((x . -226.146356971011) (y . 134.765768982315))) (end . ((x . -221.160377069713) (y . 134.765768982315)))))
  ("LINE" "CACEM - LINEE SCHEDA" ((start . ((x . -226.146362934222) (y . 134.205593839794))) (end . ((x . -221.160376984541) (y . 134.205593839794)))))
  ("LINE" "CACEM - LINEE SCHEDA" ((start . ((x . -226.146344957488) (y . 133.037553323388))) (end . ((x . -221.160376643879) (y . 133.037553323388)))))
  ("LINE" "CACEM - LINEE SCHEDA" ((start . ((x . -226.146344957488) (y . 132.401060064242))) (end . ((x . -221.160376476146) (y . 132.401060064242)))))
  ("LINE" "CACEM - LINEE SCHEDA" ((start . ((x . -226.146309004019) (y . 125.063252719199))) (end . ((x . -221.160377436599) (y . 125.063252719199)))))
  ("LINE" "CACEM - LINEE SCHEDA" ((start . ((x . -216.058600038062) (y . 124.679900636487))) (end . ((x . -210.301836821052) (y . 124.679900636487)))))
  ("LWPOLYLINE" "CACEM - LINEE SCHEDA" ((vertices . (((x . -210.541045971285) (y . 126.198457722977)))) (bulges . ()) (closed . T)))
  ("LINE" "CACEM - LINEE SCHEDA" ((start . ((x . -214.304398997165) (y . 126.29734889029))) (end . ((x . -214.304398997165) (y . 124.520428029151)))))
  ("LINE" "CACEM - LINEE SCHEDA" ((start . ((x . -215.899126665259) (y . 125.158319255841))) (end . ((x . -215.899126665259) (y . 124.520428029151)))))
  ("LINE" "CACEM - LINEE SCHEDA" ((start . ((x . -210.541045971285) (y . 125.078582553502))) (end . ((x . -210.541045971285) (y . 124.520428029151)))))
  ("LINE" "CACEM - LINEE SCHEDA" ((start . ((x . -212.135773639378) (y . 124.520428029151))) (end . ((x . -212.135773639378) (y . 126.29734889029)))))
  ("LINE" "CACEM - LINEE SCHEDA" ((start . ((x . -213.478813809322) (y . 121.806268039407))) (end . ((x . -210.055177381886) (y . 121.806268039407)))))
  ("LINE" "CACEM - LINEE SCHEDA" ((start . ((x . -213.478813809322) (y . 123.058475170044))) (end . ((x . -210.055177381886) (y . 123.058475170044)))))
  ("LINE" "CACEM - LINEE SCHEDA" ((start . ((x . -213.478813809322) (y . 122.432371391477))) (end . ((x . -210.055177381886) (y . 122.432371391477)))))
  ("LINE" "CACEM - LINEE SCHEDA" ((start . ((x . -213.478813809322) (y . 122.119319715437))) (end . ((x . -210.055177381886) (y . 122.119319715437)))))
  ("LINE" "CACEM - LINEE SCHEDA" ((start . ((x . -213.478813809322) (y . 122.745423067506))) (end . ((x . -210.055177381886) (y . 122.745423067506)))))
  ("LINE" "CACEM - LINEE SCHEDA" ((start . ((x . -212.43769676367) (y . 121.493216363377))) (end . ((x . -212.437696763675) (y . 123.058475170044)))))
  ("LINE" "CACEM - LINEE SCHEDA" ((start . ((x . -211.811592985108) (y . 121.493216363377))) (end . ((x . -211.811592985108) (y . 123.058475170044)))))
  ("LINE" "CACEM - LINEE SCHEDA" ((start . ((x . -211.185489633044) (y . 121.493216363377))) (end . ((x . -211.185489633044) (y . 123.058475170044)))))
  ("LINE" "CACEM - LINEE SCHEDA" ((start . ((x . -210.527773054801) (y . 121.493216363377))) (end . ((x . -210.527773054801) (y . 123.058475170044)))))
  ("LINE" "CACEM - LINEE SCHEDA" ((start . ((x . -214.032735735701) (y . 121.493216363377))) (end . ((x . -214.032735735701) (y . 123.058475170044)))))
  ("LINE" "CACEM - LINEE SCHEDA" ((start . ((x . -214.907527922633) (y . 121.493216363377))) (end . ((x . -214.907527922633) (y . 123.058475170044)))))
  ("LINE" "CACEM - LINEE SCHEDA" ((start . ((x . -213.536175449667) (y . 123.058475170044))) (end . ((x . -216.384994355256) (y . 123.058475170044)))))
  ("LINE" "CACEM - LINEE SCHEDA" ((start . ((x . -213.536175852163) (y . 122.723390153959))) (end . ((x . -214.907527867978) (y . 122.723390153959)))))
  ("LINE" "CACEM - LINEE SCHEDA" ((start . ((x . -213.536175931666) (y . 122.12710113444))) (end . ((x . -214.907527947475) (y . 122.12710113444)))))
  ("LINE" "CACEM - LINEE SCHEDA" ((start . ((x . -225.928031797623) (y . 128.068280353516))) (end . ((x . -221.160340522677) (y . 128.068280353516)))))
  ("LINE" "CACEM - LINEE SCHEDA" ((start . ((x . -226.146326980753) (y . 130.051584007657))) (end . ((x . -221.160358667144) (y . 130.051584007657)))))
  ("LINE" "CACEM - LINEE SCHEDA" ((start . ((x . -225.928031797623) (y . 128.706587350078))) (end . ((x . -221.160340522677) (y . 128.706587350078)))))
  ("LINE" "CACEM - LINEE SCHEDA" ((start . ((x . -226.146309004019) (y . 127.216371679808))) (end . ((x . -221.160340522677) (y . 127.216371679808)))))
  ("LINE" "CACEM - LINEE SCHEDA" ((start . ((x . -226.146309004019) (y . 126.268148405799))) (end . ((x . -221.160340522677) (y . 126.268148405799)))))
  ("LINE" "CACEM - LINEE SCHEDA" ((start . ((x . -226.146344957488) (y . 130.585536641358))) (end . ((x . -221.160376476146) (y . 130.585536641358)))))
  ("LINE" "CACEM - LINEE SCHEDA" ((start . ((x . -226.146344957488) (y . 131.188615745938))) (end . ((x . -221.160376643879) (y . 131.188615745938)))))
  ("LINE" "CACEM - LINEE SCHEDA" ((start . ((x . -221.045327181226) (y . 126.188712850956))) (end . ((x . -216.500045510033) (y . 126.188712850956)))))
  ("LINE" "CACEM - LINEE SCHEDA" ((start . ((x . -206.558819189759) (y . 121.459884661816))) (end . ((x . -206.558819189759) (y . 124.46849609875)))))
  ("LINE" "CACEM - LINEE SCHEDA" ((start . ((x . -203.900124437403) (y . 121.459884661816))) (end . ((x . -203.900124437403) (y . 124.46849609875)))))
  ("LINE" "CACEM - LINEE SCHEDA" ((start . ((x . -209.888447123228) (y . 121.459884661816))) (end . ((x . -209.888447123228) (y . 124.46849609875)))))
  ("LINE" "CACEM - LINEE SCHEDA" ((start . ((x . -209.888447123228) (y . 121.459884661816))) (end . ((x . -203.900124437403) (y . 121.459884661816)))))
  ("LINE" "CACEM - LINEE SCHEDA" ((start . ((x . -209.888447123228) (y . 122.531082215606))) (end . ((x . -203.900124437403) (y . 122.531082215606)))))
  ("LINE" "CACEM - LINEE SCHEDA" ((start . ((x . -209.888447123228) (y . 122.879224211009))) (end . ((x . -206.558819189759) (y . 122.879224211009)))))
  ("LINE" "CACEM - LINEE SCHEDA" ((start . ((x . -209.888447123228) (y . 122.705153213307))) (end . ((x . -206.558819189759) (y . 122.705153213307)))))
  ("LINE" "CACEM - LINEE SCHEDA" ((start . ((x . -209.888447123228) (y . 123.505879802736))) (end . ((x . -203.900124437403) (y . 123.505879802736)))))
  ("LINE" "CACEM - LINEE SCHEDA" ((start . ((x . -209.888447123228) (y . 123.227366206413))) (end . ((x . -206.558819189759) (y . 123.227366206413)))))
  ("LINE" "CACEM - LINEE SCHEDA" ((start . ((x . -209.888447123228) (y . 123.053295208711))) (end . ((x . -206.558819189759) (y . 123.053295208711)))))
  ("LINE" "CACEM - LINEE SCHEDA" ((start . ((x . -209.888447123228) (y . 124.46849609875))) (end . ((x . -203.900124437403) (y . 124.46849609875)))))
  ("LINE" "CACEM - LINEE SCHEDA" ((start . ((x . -208.976570878158) (y . 122.531082215606))) (end . ((x . -208.976570878158) (y . 123.227366206413)))))
  ("LINE" "CACEM - LINEE SCHEDA" ((start . ((x . -208.000067539081) (y . 122.531082215606))) (end . ((x . -208.000067539081) (y . 123.227366206413)))))
  ("LINE" "CACEM - LINEE SCHEDA" ((start . ((x . -207.297279608181) (y . 122.531082215606))) (end . ((x . -207.297279608181) (y . 123.227366206413)))))
  ("LINE" "CACEM - LINEE SCHEDA" ((start . ((x . -209.888447123228) (y . 124.872226690808))) (end . ((x . -203.900124437403) (y . 124.872226690808)))))
  ("LINE" "CACEM - LINEE SCHEDA" ((start . ((x . -209.888447123228) (y . 124.514624682827))) (end . ((x . -203.900124437403) (y . 124.514624682827)))))
  ("LINE" "CACEM - LINEE SCHEDA" ((start . ((x . -209.888447123228) (y . 125.286658815391))) (end . ((x . -203.900124437403) (y . 125.286658815391)))))
  ("LINE" "CACEM - LINEE SCHEDA" ((start . ((x . -209.888447123228) (y . 124.514624682827))) (end . ((x . -209.888447123228) (y . 125.286658815391)))))
  ("LINE" "CACEM - LINEE SCHEDA" ((start . ((x . -208.66231264696) (y . 124.514624682827))) (end . ((x . -208.66231264696) (y . 125.286658815391)))))
  ("LINE" "CACEM - LINEE SCHEDA" ((start . ((x . -208.107847225585) (y . 124.514624682827))) (end . ((x . -208.107847225585) (y . 125.286658815391)))))
  ("LINE" "CACEM - LINEE SCHEDA" ((start . ((x . -207.339222040928) (y . 124.514624682827))) (end . ((x . -207.339222040928) (y . 125.286658815391)))))
  ("LINE" "CACEM - LINEE SCHEDA" ((start . ((x . -206.57059685627) (y . 124.514624682827))) (end . ((x . -206.57059685627) (y . 125.286658815391)))))
  ("LINE" "CACEM - LINEE SCHEDA" ((start . ((x . -205.801971671612) (y . 124.514624682827))) (end . ((x . -205.801971671612) (y . 125.286658815391)))))
  ("LINE" "CACEM - LINEE SCHEDA" ((start . ((x . -205.229654401716) (y . 124.514624682827))) (end . ((x . -205.229654401716) (y . 125.286658815391)))))
  ("LINE" "CACEM - LINEE SCHEDA" ((start . ((x . -204.585960947231) (y . 124.514624682827))) (end . ((x . -204.585960947231) (y . 125.286658815391)))))
  ("LINE" "CACEM - LINEE SCHEDA" ((start . ((x . -203.900124437403) (y . 124.514624682827))) (end . ((x . -203.900124437403) (y . 125.286658815391)))))
  ("LINE" "CACEM - LINEE SCHEDA" ((start . ((x . -206.048960112255) (y . 124.318841347269))) (end . ((x . -206.150053987627) (y . 124.37720792343)))))
  ("LINE" "CACEM - LINEE SCHEDA" ((start . ((x . -206.048960112255) (y . 124.309113584576))) (end . ((x . -206.150053987627) (y . 124.367480160736)))))
  ("LINE" "CACEM - LINEE SCHEDA" ((start . ((x . -206.048960112255) (y . 124.260474771109))) (end . ((x . -206.099507049942) (y . 124.28965805919)))))
  ("LINE" "CACEM - LINEE SCHEDA" ((start . ((x . -206.048960112255) (y . 124.250747008416))) (end . ((x . -206.099507049942) (y . 124.279930296496)))))
  ("LINE" "CACEM - LINEE SCHEDA" ((start . ((x . -206.048960112255) (y . 124.231291483029))) (end . ((x . -206.099507049942) (y . 124.260474771109)))))
  ("LINE" "CACEM - LINEE SCHEDA" ((start . ((x . -206.048960112255) (y . 124.221563720336))) (end . ((x . -206.099507049942) (y . 124.250747008416)))))
  ("LINE" "CACEM - LINEE SCHEDA" ((start . ((x . -206.048960112255) (y . 124.241019245723))) (end . ((x . -206.099507049942) (y . 124.270202533803)))))
  ("LINE" "CACEM - LINEE SCHEDA" ((start . ((x . -206.048960112255) (y . 124.299385821882))) (end . ((x . -206.150053987627) (y . 124.357752398043)))))
  ("LINE" "CACEM - LINEE SCHEDA" ((start . ((x . -206.048960112255) (y . 124.28965805919))) (end . ((x . -206.150053987627) (y . 124.34802463535)))))
  ("LINE" "CACEM - LINEE SCHEDA" ((start . ((x . -206.048960112255) (y . 124.279930296496))) (end . ((x . -206.150053987627) (y . 124.338296872657)))))
  ("LINE" "CACEM - LINEE SCHEDA" ((start . ((x . -206.048960112255) (y . 124.270202533803))) (end . ((x . -206.099507049942) (y . 124.299385821882)))))
  ("LINE" "CACEM - LINEE SCHEDA" ((start . ((x . -206.048960112255) (y . 124.328569109963))) (end . ((x . -206.150053987627) (y . 124.386935686123)))))
  ("LINE" "CACEM - LINEE SCHEDA" ((start . ((x . -206.048960112255) (y . 124.386935686123))) (end . ((x . -206.099507049942) (y . 124.416118974203)))))
  ("LINE" "CACEM - LINEE SCHEDA" ((start . ((x . -206.200600925314) (y . 124.231291483029))) (end . ((x . -206.301694800689) (y . 124.28965805919)))))
  ("LINE" "CACEM - LINEE SCHEDA" ((start . ((x . -206.200600925314) (y . 124.221563720336))) (end . ((x . -206.301694800689) (y . 124.279930296496)))))
  ("LINE" "CACEM - LINEE SCHEDA" ((start . ((x . -206.200600925314) (y . 124.241019245723))) (end . ((x . -206.301694800689) (y . 124.299385821882)))))
  ("LINE" "CACEM - LINEE SCHEDA" ((start . ((x . -206.150053987627) (y . 124.386935686123))) (end . ((x . -206.099507049942) (y . 124.416118974203)))))
  ("LINE" "CACEM - LINEE SCHEDA" ((start . ((x . -206.150053987627) (y . 124.328569109963))) (end . ((x . -206.150053987627) (y . 124.386935686123)))))
  ("LINE" "CACEM - LINEE SCHEDA" ((start . ((x . -206.200600925314) (y . 124.241019245723))) (end . ((x . -206.099507049942) (y . 124.299385821882)))))
  ("LINE" "CACEM - LINEE SCHEDA" ((start . ((x . -206.099507049942) (y . 124.299385821882))) (end . ((x . -206.099507049942) (y . 124.241019245723)))))
  ("LINE" "CACEM - LINEE SCHEDA" ((start . ((x . -206.200600925314) (y . 124.299385821882))) (end . ((x . -206.150053987627) (y . 124.328569109963)))))
  ("LINE" "CACEM - LINEE SCHEDA" ((start . ((x . -206.099507049942) (y . 124.299385821882))) (end . ((x . -206.150053987627) (y . 124.328569109963)))))
  ("LINE" "CACEM - LINEE SCHEDA" ((start . ((x . -206.301694800689) (y . 124.241019245723))) (end . ((x . -206.301694800689) (y . 124.299385821882)))))
  ("LINE" "CACEM - LINEE SCHEDA" ((start . ((x . -206.301694800689) (y . 124.299385821882))) (end . ((x . -206.251147862999) (y . 124.328569109963)))))
  ("LINE" "CACEM - LINEE SCHEDA" ((start . ((x . -206.200600925314) (y . 124.299385821882))) (end . ((x . -206.251147862999) (y . 124.328569109963)))))
  ("LINE" "CACEM - LINEE SCHEDA" ((start . ((x . -205.897319299195) (y . 124.241019245723))) (end . ((x . -205.796225423822) (y . 124.299385821882)))))
  ("LINE" "CACEM - LINEE SCHEDA" ((start . ((x . -205.897319299195) (y . 124.299385821882))) (end . ((x . -205.846772361509) (y . 124.328569109963)))))
  ("LINE" "CACEM - LINEE SCHEDA" ((start . ((x . -206.048960112255) (y . 124.386935686123))) (end . ((x . -205.998413174569) (y . 124.416118974203)))))
  ("LINE" "CACEM - LINEE SCHEDA" ((start . ((x . -206.048960112255) (y . 124.328569109963))) (end . ((x . -205.947866236883) (y . 124.386935686123)))))
  ("LINE" "CACEM - LINEE SCHEDA" ((start . ((x . -205.897319299195) (y . 124.299385821882))) (end . ((x . -205.947866236883) (y . 124.328569109963)))))
  ("LINE" "CACEM - LINEE SCHEDA" ((start . ((x . -205.947866236883) (y . 124.386935686123))) (end . ((x . -205.947866236883) (y . 124.328569109963)))))
  ("LINE" "CACEM - LINEE SCHEDA" ((start . ((x . -205.998413174569) (y . 124.241019245723))) (end . ((x . -205.998413174569) (y . 124.299385821882)))))
  ("LINE" "CACEM - LINEE SCHEDA" ((start . ((x . -205.897319299195) (y . 124.231291483029))) (end . ((x . -205.998413174569) (y . 124.28965805919)))))
  ("LINE" "CACEM - LINEE SCHEDA" ((start . ((x . -205.897319299195) (y . 124.221563720336))) (end . ((x . -205.998413174569) (y . 124.279930296496)))))
  ("LINE" "CACEM - LINEE SCHEDA" ((start . ((x . -205.998413174569) (y . 124.299385821882))) (end . ((x . -205.947866236883) (y . 124.328569109963)))))
  ("LINE" "CACEM - LINEE SCHEDA" ((start . ((x . -205.947866236883) (y . 124.386935686123))) (end . ((x . -205.998413174569) (y . 124.416118974203)))))
  ("LINE" "CACEM - LINEE SCHEDA" ((start . ((x . -205.897319299195) (y . 124.241019245723))) (end . ((x . -205.998413174569) (y . 124.299385821882)))))
  ("LINE" "CACEM - LINEE SCHEDA" ((start . ((x . -205.796225423822) (y . 124.299385821882))) (end . ((x . -205.846772361509) (y . 124.328569109963)))))
  ("LINE" "CACEM - LINEE SCHEDA" ((start . ((x . -205.796225423822) (y . 124.299385821882))) (end . ((x . -205.796225423822) (y . 124.241019245723)))))
  ("LINE" "CACEM - LINEE SCHEDA" ((start . ((x . -206.048960112255) (y . 124.085375042628))) (end . ((x . -206.099507049942) (y . 124.114558330709)))))
  ("LINE" "CACEM - LINEE SCHEDA" ((start . ((x . -206.048960112255) (y . 124.075647279935))) (end . ((x . -206.099507049942) (y . 124.104830568015)))))
  ("LINE" "CACEM - LINEE SCHEDA" ((start . ((x . -206.048960112255) (y . 124.065919517242))) (end . ((x . -206.099507049942) (y . 124.095102805322)))))
  ("LINE" "CACEM - LINEE SCHEDA" ((start . ((x . -206.048960112255) (y . 124.056191754549))) (end . ((x . -206.099507049942) (y . 124.085375042628)))))
  ("LINE" "CACEM - LINEE SCHEDA" ((start . ((x . -206.048960112255) (y . 124.046463991855))) (end . ((x . -206.099507049942) (y . 124.075647279935)))))
  ("LINE" "CACEM - LINEE SCHEDA" ((start . ((x . -206.048960112255) (y . 124.095102805322))) (end . ((x . -206.099507049942) (y . 124.124286093402)))))
  ("LINE" "CACEM - LINEE SCHEDA" ((start . ((x . -206.048960112255) (y . 124.124286093402))) (end . ((x . -206.150053987627) (y . 124.182652669563)))))
  ("LINE" "CACEM - LINEE SCHEDA" ((start . ((x . -206.048960112255) (y . 124.104830568015))) (end . ((x . -206.150053987627) (y . 124.163197144176)))))
  ("LINE" "CACEM - LINEE SCHEDA" ((start . ((x . -206.048960112255) (y . 124.114558330709))) (end . ((x . -206.150053987627) (y . 124.172924906869)))))
  ("LINE" "CACEM - LINEE SCHEDA" ((start . ((x . -206.048960112255) (y . 124.143741618788))) (end . ((x . -206.150053987627) (y . 124.202108194949)))))
  ("LINE" "CACEM - LINEE SCHEDA" ((start . ((x . -206.048960112255) (y . 124.134013856095))) (end . ((x . -206.150053987627) (y . 124.192380432255)))))
  ("LINE" "CACEM - LINEE SCHEDA" ((start . ((x . -206.048960112255) (y . 124.036736229162))) (end . ((x . -206.099507049942) (y . 124.065919517242)))))
  ("LINE" "CACEM - LINEE SCHEDA" ((start . ((x . -206.048960112255) (y . 124.153469381483))) (end . ((x . -206.150053987627) (y . 124.211835957643)))))
  ("LINE" "CACEM - LINEE SCHEDA" ((start . ((x . -206.200600925314) (y . 124.124286093402))) (end . ((x . -206.150053987627) (y . 124.153469381483)))))
  ("LINE" "CACEM - LINEE SCHEDA" ((start . ((x . -206.099507049942) (y . 124.124286093402))) (end . ((x . -206.099507049942) (y . 124.065919517242)))))
  ("LINE" "CACEM - LINEE SCHEDA" ((start . ((x . -206.150053987627) (y . 124.153469381483))) (end . ((x . -206.150053987627) (y . 124.211835957643)))))
  ("LINE" "CACEM - LINEE SCHEDA" ((start . ((x . -206.099507049942) (y . 124.124286093402))) (end . ((x . -206.150053987627) (y . 124.153469381483)))))
  ("LINE" "CACEM - LINEE SCHEDA" ((start . ((x . -206.251147862999) (y . 124.211835957643))) (end . ((x . -206.251147862999) (y . 124.153469381483)))))
  ("LINE" "CACEM - LINEE SCHEDA" ((start . ((x . -206.200600925314) (y . 124.182652669563))) (end . ((x . -206.251147862999) (y . 124.211835957643)))))
  ("LINE" "CACEM - LINEE SCHEDA" ((start . ((x . -206.200600925314) (y . 124.172924906869))) (end . ((x . -206.251147862999) (y . 124.202108194949)))))
  ("LINE" "CACEM - LINEE SCHEDA" ((start . ((x . -206.200600925314) (y . 124.163197144176))) (end . ((x . -206.251147862999) (y . 124.192380432255)))))
  ("LINE" "CACEM - LINEE SCHEDA" ((start . ((x . -206.200600925314) (y . 124.153469381483))) (end . ((x . -206.251147862999) (y . 124.182652669563)))))
  ("LINE" "CACEM - LINEE SCHEDA" ((start . ((x . -206.200600925314) (y . 124.143741618788))) (end . ((x . -206.251147862999) (y . 124.172924906869)))))
  ("LINE" "CACEM - LINEE SCHEDA" ((start . ((x . -206.200600925314) (y . 124.134013856095))) (end . ((x . -206.251147862999) (y . 124.163197144176)))))
  ("LINE" "CACEM - LINEE SCHEDA" ((start . ((x . -206.200600925314) (y . 124.124286093402))) (end . ((x . -206.251147862999) (y . 124.153469381483)))))
  ("LINE" "CACEM - LINEE SCHEDA" ((start . ((x . -205.897319299195) (y . 124.124286093402))) (end . ((x . -205.846772361509) (y . 124.153469381483)))))
  ("LINE" "CACEM - LINEE SCHEDA" ((start . ((x . -206.048960112255) (y . 124.036736229162))) (end . ((x . -205.998413174569) (y . 124.065919517242)))))
  ("LINE" "CACEM - LINEE SCHEDA" ((start . ((x . -206.048960112255) (y . 124.153469381483))) (end . ((x . -205.947866236883) (y . 124.211835957643)))))
  ("LINE" "CACEM - LINEE SCHEDA" ((start . ((x . -206.048960112255) (y . 124.153469381483))) (end . ((x . -206.048960112255) (y . 124.036736229162)))))
  ("LINE" "CACEM - LINEE SCHEDA" ((start . ((x . -205.897319299195) (y . 124.153469381483))) (end . ((x . -205.947866236883) (y . 124.182652669563)))))
  ("LINE" "CACEM - LINEE SCHEDA" ((start . ((x . -205.897319299195) (y . 124.182652669563))) (end . ((x . -205.947866236883) (y . 124.211835957643)))))
  ("LINE" "CACEM - LINEE SCHEDA" ((start . ((x . -205.897319299195) (y . 124.172924906869))) (end . ((x . -205.947866236883) (y . 124.202108194949)))))
  ("LINE" "CACEM - LINEE SCHEDA" ((start . ((x . -205.897319299195) (y . 124.163197144176))) (end . ((x . -205.947866236883) (y . 124.192380432255)))))
  ("LINE" "CACEM - LINEE SCHEDA" ((start . ((x . -205.897319299195) (y . 124.143741618788))) (end . ((x . -205.947866236883) (y . 124.172924906869)))))
  ("LINE" "CACEM - LINEE SCHEDA" ((start . ((x . -205.897319299195) (y . 124.134013856095))) (end . ((x . -205.947866236883) (y . 124.163197144176)))))
  ("LINE" "CACEM - LINEE SCHEDA" ((start . ((x . -205.947866236883) (y . 124.211835957643))) (end . ((x . -205.947866236883) (y . 124.153469381483)))))
  ("LINE" "CACEM - LINEE SCHEDA" ((start . ((x . -205.897319299195) (y . 124.124286093402))) (end . ((x . -205.947866236883) (y . 124.153469381483)))))
  ("LINE" "CACEM - LINEE SCHEDA" ((start . ((x . -205.998413174569) (y . 124.124286093402))) (end . ((x . -205.998413174569) (y . 124.065919517242)))))
  ("LINE" "CACEM - LINEE SCHEDA" ((start . ((x . -205.998413174569) (y . 124.124286093402))) (end . ((x . -205.947866236883) (y . 124.153469381483)))))
  ("LINE" "CACEM - LINEE SCHEDA" ((start . ((x . -205.846772361509) (y . 124.211835957643))) (end . ((x . -205.846772361509) (y . 124.153469381483)))))
  ("LINE" "CACEM - LINEE SCHEDA" ((start . ((x . -206.048960112255) (y . 124.211835957643))) (end . ((x . -206.099507049942) (y . 124.241019245723)))))
  ("LINE" "CACEM - LINEE SCHEDA" ((start . ((x . -206.200600925314) (y . 124.202108194949))) (end . ((x . -206.301694800689) (y . 124.260474771109)))))
  ("LINE" "CACEM - LINEE SCHEDA" ((start . ((x . -206.200600925314) (y . 124.192380432255))) (end . ((x . -206.301694800689) (y . 124.250747008416)))))
  ("LINE" "CACEM - LINEE SCHEDA" ((start . ((x . -206.200600925314) (y . 124.211835957643))) (end . ((x . -206.301694800689) (y . 124.270202533803)))))
  ("LINE" "CACEM - LINEE SCHEDA" ((start . ((x . -206.200600925314) (y . 124.241019245723))) (end . ((x . -206.200600925314) (y . 124.124286093402)))))
  ("LINE" "CACEM - LINEE SCHEDA" ((start . ((x . -206.150053987627) (y . 124.211835957643))) (end . ((x . -206.099507049942) (y . 124.241019245723)))))
  ("LINE" "CACEM - LINEE SCHEDA" ((start . ((x . -206.251147862999) (y . 124.211835957643))) (end . ((x . -206.301694800689) (y . 124.241019245723)))))
  ("LINE" "CACEM - LINEE SCHEDA" ((start . ((x . -206.048960112255) (y . 124.211835957643))) (end . ((x . -205.998413174569) (y . 124.241019245723)))))
  ("LINE" "CACEM - LINEE SCHEDA" ((start . ((x . -206.048960112255) (y . 124.328569109963))) (end . ((x . -206.048960112255) (y . 124.211835957643)))))
  ("LINE" "CACEM - LINEE SCHEDA" ((start . ((x . -205.897319299195) (y . 124.241019245723))) (end . ((x . -205.897319299195) (y . 124.124286093402)))))
  ("LINE" "CACEM - LINEE SCHEDA" ((start . ((x . -205.897319299195) (y . 124.202108194949))) (end . ((x . -205.998413174569) (y . 124.260474771109)))))
  ("LINE" "CACEM - LINEE SCHEDA" ((start . ((x . -205.897319299195) (y . 124.192380432255))) (end . ((x . -205.998413174569) (y . 124.250747008416)))))
  ("LINE" "CACEM - LINEE SCHEDA" ((start . ((x . -205.897319299195) (y . 124.211835957643))) (end . ((x . -205.998413174569) (y . 124.270202533803)))))
  ("LINE" "CACEM - LINEE SCHEDA" ((start . ((x . -205.947866236883) (y . 124.211835957643))) (end . ((x . -205.998413174569) (y . 124.241019245723)))))
  ("LINE" "CACEM - LINEE SCHEDA" ((start . ((x . -205.846772361509) (y . 124.211835957643))) (end . ((x . -205.796225423822) (y . 124.241019245723)))))
  ("LINE" "CACEM - LINEE SCHEDA" ((start . ((x . -206.048960112255) (y . 124.318841347269))) (end . ((x . -206.150053987627) (y . 124.37720792343)))))
  ("LINE" "CACEM - LINEE SCHEDA" ((start . ((x . -206.048960112255) (y . 124.309113584576))) (end . ((x . -206.150053987627) (y . 124.367480160736)))))
  ("LINE" "CACEM - LINEE SCHEDA" ((start . ((x . -206.048960112255) (y . 124.260474771109))) (end . ((x . -206.099507049942) (y . 124.28965805919)))))
  ("LINE" "CACEM - LINEE SCHEDA" ((start . ((x . -206.048960112255) (y . 124.250747008416))) (end . ((x . -206.099507049942) (y . 124.279930296496)))))
  ("LINE" "CACEM - LINEE SCHEDA" ((start . ((x . -206.048960112255) (y . 124.231291483029))) (end . ((x . -206.099507049942) (y . 124.260474771109)))))
  ("LINE" "CACEM - LINEE SCHEDA" ((start . ((x . -206.048960112255) (y . 124.221563720336))) (end . ((x . -206.099507049942) (y . 124.250747008416)))))
  ("LINE" "CACEM - LINEE SCHEDA" ((start . ((x . -206.048960112255) (y . 124.241019245723))) (end . ((x . -206.099507049942) (y . 124.270202533803)))))
  ("LINE" "CACEM - LINEE SCHEDA" ((start . ((x . -206.048960112255) (y . 124.299385821882))) (end . ((x . -206.150053987627) (y . 124.357752398043)))))
  ("LINE" "CACEM - LINEE SCHEDA" ((start . ((x . -206.048960112255) (y . 124.28965805919))) (end . ((x . -206.150053987627) (y . 124.34802463535)))))
  ("LINE" "CACEM - LINEE SCHEDA" ((start . ((x . -206.048960112255) (y . 124.279930296496))) (end . ((x . -206.150053987627) (y . 124.338296872657)))))
  ("LINE" "CACEM - LINEE SCHEDA" ((start . ((x . -206.048960112255) (y . 124.270202533803))) (end . ((x . -206.099507049942) (y . 124.299385821882)))))
  ("LINE" "CACEM - LINEE SCHEDA" ((start . ((x . -206.048960112255) (y . 124.328569109963))) (end . ((x . -206.150053987627) (y . 124.386935686123)))))
  ("LINE" "CACEM - LINEE SCHEDA" ((start . ((x . -206.048960112255) (y . 124.386935686123))) (end . ((x . -206.099507049942) (y . 124.416118974203)))))
  ("LINE" "CACEM - LINEE SCHEDA" ((start . ((x . -206.200600925314) (y . 124.231291483029))) (end . ((x . -206.301694800689) (y . 124.28965805919)))))
  ("LINE" "CACEM - LINEE SCHEDA" ((start . ((x . -206.200600925314) (y . 124.221563720336))) (end . ((x . -206.301694800689) (y . 124.279930296496)))))
  ("LINE" "CACEM - LINEE SCHEDA" ((start . ((x . -206.200600925314) (y . 124.241019245723))) (end . ((x . -206.301694800689) (y . 124.299385821882)))))
  ("LINE" "CACEM - LINEE SCHEDA" ((start . ((x . -206.150053987627) (y . 124.386935686123))) (end . ((x . -206.099507049942) (y . 124.416118974203)))))
  ("LINE" "CACEM - LINEE SCHEDA" ((start . ((x . -206.150053987627) (y . 124.328569109963))) (end . ((x . -206.150053987627) (y . 124.386935686123)))))
  ("LINE" "CACEM - LINEE SCHEDA" ((start . ((x . -206.200600925314) (y . 124.241019245723))) (end . ((x . -206.099507049942) (y . 124.299385821882)))))
  ("LINE" "CACEM - LINEE SCHEDA" ((start . ((x . -206.099507049942) (y . 124.299385821882))) (end . ((x . -206.099507049942) (y . 124.241019245723)))))
  ("LINE" "CACEM - LINEE SCHEDA" ((start . ((x . -206.200600925314) (y . 124.299385821882))) (end . ((x . -206.150053987627) (y . 124.328569109963)))))
  ("LINE" "CACEM - LINEE SCHEDA" ((start . ((x . -206.099507049942) (y . 124.299385821882))) (end . ((x . -206.150053987627) (y . 124.328569109963)))))
  ("LINE" "CACEM - LINEE SCHEDA" ((start . ((x . -206.301694800689) (y . 124.241019245723))) (end . ((x . -206.301694800689) (y . 124.299385821882)))))
  ("LINE" "CACEM - LINEE SCHEDA" ((start . ((x . -206.301694800689) (y . 124.299385821882))) (end . ((x . -206.251147862999) (y . 124.328569109963)))))
  ("LINE" "CACEM - LINEE SCHEDA" ((start . ((x . -206.200600925314) (y . 124.299385821882))) (end . ((x . -206.251147862999) (y . 124.328569109963)))))
  ("LINE" "CACEM - LINEE SCHEDA" ((start . ((x . -205.897319299195) (y . 124.241019245723))) (end . ((x . -205.796225423822) (y . 124.299385821882)))))
  ("LINE" "CACEM - LINEE SCHEDA" ((start . ((x . -205.897319299195) (y . 124.299385821882))) (end . ((x . -205.846772361509) (y . 124.328569109963)))))
  ("LINE" "CACEM - LINEE SCHEDA" ((start . ((x . -206.048960112255) (y . 124.386935686123))) (end . ((x . -205.998413174569) (y . 124.416118974203)))))
  ("LINE" "CACEM - LINEE SCHEDA" ((start . ((x . -206.048960112255) (y . 124.328569109963))) (end . ((x . -205.947866236883) (y . 124.386935686123)))))
  ("LINE" "CACEM - LINEE SCHEDA" ((start . ((x . -205.897319299195) (y . 124.299385821882))) (end . ((x . -205.947866236883) (y . 124.328569109963)))))
  ("LINE" "CACEM - LINEE SCHEDA" ((start . ((x . -205.947866236883) (y . 124.386935686123))) (end . ((x . -205.947866236883) (y . 124.328569109963)))))
  ("LINE" "CACEM - LINEE SCHEDA" ((start . ((x . -205.998413174569) (y . 124.241019245723))) (end . ((x . -205.998413174569) (y . 124.299385821882)))))
  ("LINE" "CACEM - LINEE SCHEDA" ((start . ((x . -205.897319299195) (y . 124.231291483029))) (end . ((x . -205.998413174569) (y . 124.28965805919)))))
  ("LINE" "CACEM - LINEE SCHEDA" ((start . ((x . -205.897319299195) (y . 124.221563720336))) (end . ((x . -205.998413174569) (y . 124.279930296496)))))
  ("LINE" "CACEM - LINEE SCHEDA" ((start . ((x . -205.998413174569) (y . 124.299385821882))) (end . ((x . -205.947866236883) (y . 124.328569109963)))))
  ("LINE" "CACEM - LINEE SCHEDA" ((start . ((x . -205.947866236883) (y . 124.386935686123))) (end . ((x . -205.998413174569) (y . 124.416118974203)))))
  ("LINE" "CACEM - LINEE SCHEDA" ((start . ((x . -205.897319299195) (y . 124.241019245723))) (end . ((x . -205.998413174569) (y . 124.299385821882)))))
  ("LINE" "CACEM - LINEE SCHEDA" ((start . ((x . -205.796225423822) (y . 124.299385821882))) (end . ((x . -205.846772361509) (y . 124.328569109963)))))
  ("LINE" "CACEM - LINEE SCHEDA" ((start . ((x . -205.796225423822) (y . 124.299385821882))) (end . ((x . -205.796225423822) (y . 124.241019245723)))))
  ("LINE" "CACEM - LINEE SCHEDA" ((start . ((x . -206.048960112255) (y . 124.085375042628))) (end . ((x . -206.099507049942) (y . 124.114558330709)))))
  ("LINE" "CACEM - LINEE SCHEDA" ((start . ((x . -206.048960112255) (y . 124.075647279935))) (end . ((x . -206.099507049942) (y . 124.104830568015)))))
  ("LINE" "CACEM - LINEE SCHEDA" ((start . ((x . -206.048960112255) (y . 124.065919517242))) (end . ((x . -206.099507049942) (y . 124.095102805322)))))
  ("LINE" "CACEM - LINEE SCHEDA" ((start . ((x . -206.048960112255) (y . 124.056191754549))) (end . ((x . -206.099507049942) (y . 124.085375042628)))))
  ("LINE" "CACEM - LINEE SCHEDA" ((start . ((x . -206.048960112255) (y . 124.046463991855))) (end . ((x . -206.099507049942) (y . 124.075647279935)))))
  ("LINE" "CACEM - LINEE SCHEDA" ((start . ((x . -206.048960112255) (y . 124.095102805322))) (end . ((x . -206.099507049942) (y . 124.124286093402)))))
  ("LINE" "CACEM - LINEE SCHEDA" ((start . ((x . -206.048960112255) (y . 124.124286093402))) (end . ((x . -206.150053987627) (y . 124.182652669563)))))
  ("LINE" "CACEM - LINEE SCHEDA" ((start . ((x . -206.048960112255) (y . 124.104830568015))) (end . ((x . -206.150053987627) (y . 124.163197144176)))))
  ("LINE" "CACEM - LINEE SCHEDA" ((start . ((x . -206.048960112255) (y . 124.114558330709))) (end . ((x . -206.150053987627) (y . 124.172924906869)))))
  ("LINE" "CACEM - LINEE SCHEDA" ((start . ((x . -206.048960112255) (y . 124.143741618788))) (end . ((x . -206.150053987627) (y . 124.202108194949)))))
  ("LINE" "CACEM - LINEE SCHEDA" ((start . ((x . -206.048960112255) (y . 124.134013856095))) (end . ((x . -206.150053987627) (y . 124.192380432255)))))
  ("LINE" "CACEM - LINEE SCHEDA" ((start . ((x . -206.048960112255) (y . 124.036736229162))) (end . ((x . -206.099507049942) (y . 124.065919517242)))))
  ("LINE" "CACEM - LINEE SCHEDA" ((start . ((x . -206.048960112255) (y . 124.153469381483))) (end . ((x . -206.150053987627) (y . 124.211835957643)))))
  ("LINE" "CACEM - LINEE SCHEDA" ((start . ((x . -206.200600925314) (y . 124.124286093402))) (end . ((x . -206.150053987627) (y . 124.153469381483)))))
  ("LINE" "CACEM - LINEE SCHEDA" ((start . ((x . -206.099507049942) (y . 124.124286093402))) (end . ((x . -206.099507049942) (y . 124.065919517242)))))
  ("LINE" "CACEM - LINEE SCHEDA" ((start . ((x . -206.150053987627) (y . 124.153469381483))) (end . ((x . -206.150053987627) (y . 124.211835957643)))))
  ("LINE" "CACEM - LINEE SCHEDA" ((start . ((x . -206.099507049942) (y . 124.124286093402))) (end . ((x . -206.150053987627) (y . 124.153469381483)))))
  ("LINE" "CACEM - LINEE SCHEDA" ((start . ((x . -206.251147862999) (y . 124.211835957643))) (end . ((x . -206.251147862999) (y . 124.153469381483)))))
  ("LINE" "CACEM - LINEE SCHEDA" ((start . ((x . -206.200600925314) (y . 124.182652669563))) (end . ((x . -206.251147862999) (y . 124.211835957643)))))
  ("LINE" "CACEM - LINEE SCHEDA" ((start . ((x . -206.200600925314) (y . 124.172924906869))) (end . ((x . -206.251147862999) (y . 124.202108194949)))))
  ("LINE" "CACEM - LINEE SCHEDA" ((start . ((x . -206.200600925314) (y . 124.163197144176))) (end . ((x . -206.251147862999) (y . 124.192380432255)))))
  ("LINE" "CACEM - LINEE SCHEDA" ((start . ((x . -206.200600925314) (y . 124.153469381483))) (end . ((x . -206.251147862999) (y . 124.182652669563)))))
  ("LINE" "CACEM - LINEE SCHEDA" ((start . ((x . -206.200600925314) (y . 124.143741618788))) (end . ((x . -206.251147862999) (y . 124.172924906869)))))
  ("LINE" "CACEM - LINEE SCHEDA" ((start . ((x . -206.200600925314) (y . 124.134013856095))) (end . ((x . -206.251147862999) (y . 124.163197144176)))))
  ("LINE" "CACEM - LINEE SCHEDA" ((start . ((x . -206.200600925314) (y . 124.124286093402))) (end . ((x . -206.251147862999) (y . 124.153469381483)))))
  ("LINE" "CACEM - LINEE SCHEDA" ((start . ((x . -205.897319299195) (y . 124.124286093402))) (end . ((x . -205.846772361509) (y . 124.153469381483)))))
  ("LINE" "CACEM - LINEE SCHEDA" ((start . ((x . -206.048960112255) (y . 124.036736229162))) (end . ((x . -205.998413174569) (y . 124.065919517242)))))
  ("LINE" "CACEM - LINEE SCHEDA" ((start . ((x . -206.048960112255) (y . 124.153469381483))) (end . ((x . -205.947866236883) (y . 124.211835957643)))))
  ("LINE" "CACEM - LINEE SCHEDA" ((start . ((x . -206.048960112255) (y . 124.153469381483))) (end . ((x . -206.048960112255) (y . 124.036736229162)))))
  ("LINE" "CACEM - LINEE SCHEDA" ((start . ((x . -205.897319299195) (y . 124.153469381483))) (end . ((x . -205.947866236883) (y . 124.182652669563)))))
  ("LINE" "CACEM - LINEE SCHEDA" ((start . ((x . -205.897319299195) (y . 124.182652669563))) (end . ((x . -205.947866236883) (y . 124.211835957643)))))
  ("LINE" "CACEM - LINEE SCHEDA" ((start . ((x . -205.897319299195) (y . 124.172924906869))) (end . ((x . -205.947866236883) (y . 124.202108194949)))))
  ("LINE" "CACEM - LINEE SCHEDA" ((start . ((x . -205.897319299195) (y . 124.163197144176))) (end . ((x . -205.947866236883) (y . 124.192380432255)))))
  ("LINE" "CACEM - LINEE SCHEDA" ((start . ((x . -205.897319299195) (y . 124.143741618788))) (end . ((x . -205.947866236883) (y . 124.172924906869)))))
  ("LINE" "CACEM - LINEE SCHEDA" ((start . ((x . -205.897319299195) (y . 124.134013856095))) (end . ((x . -205.947866236883) (y . 124.163197144176)))))
  ("LINE" "CACEM - LINEE SCHEDA" ((start . ((x . -205.947866236883) (y . 124.211835957643))) (end . ((x . -205.947866236883) (y . 124.153469381483)))))
  ("LINE" "CACEM - LINEE SCHEDA" ((start . ((x . -205.897319299195) (y . 124.124286093402))) (end . ((x . -205.947866236883) (y . 124.153469381483)))))
  ("LINE" "CACEM - LINEE SCHEDA" ((start . ((x . -205.998413174569) (y . 124.124286093402))) (end . ((x . -205.998413174569) (y . 124.065919517242)))))
  ("LINE" "CACEM - LINEE SCHEDA" ((start . ((x . -205.998413174569) (y . 124.124286093402))) (end . ((x . -205.947866236883) (y . 124.153469381483)))))
  ("LINE" "CACEM - LINEE SCHEDA" ((start . ((x . -205.846772361509) (y . 124.211835957643))) (end . ((x . -205.846772361509) (y . 124.153469381483)))))
  ("LINE" "CACEM - LINEE SCHEDA" ((start . ((x . -206.048960112255) (y . 124.211835957643))) (end . ((x . -206.099507049942) (y . 124.241019245723)))))
  ("LINE" "CACEM - LINEE SCHEDA" ((start . ((x . -206.200600925314) (y . 124.202108194949))) (end . ((x . -206.301694800689) (y . 124.260474771109)))))
  ("LINE" "CACEM - LINEE SCHEDA" ((start . ((x . -206.200600925314) (y . 124.192380432255))) (end . ((x . -206.301694800689) (y . 124.250747008416)))))
  ("LINE" "CACEM - LINEE SCHEDA" ((start . ((x . -206.200600925314) (y . 124.211835957643))) (end . ((x . -206.301694800689) (y . 124.270202533803)))))
  ("LINE" "CACEM - LINEE SCHEDA" ((start . ((x . -206.200600925314) (y . 124.241019245723))) (end . ((x . -206.200600925314) (y . 124.124286093402)))))
  ("LINE" "CACEM - LINEE SCHEDA" ((start . ((x . -206.150053987627) (y . 124.211835957643))) (end . ((x . -206.099507049942) (y . 124.241019245723)))))
  ("LINE" "CACEM - LINEE SCHEDA" ((start . ((x . -206.251147862999) (y . 124.211835957643))) (end . ((x . -206.301694800689) (y . 124.241019245723)))))
  ("LINE" "CACEM - LINEE SCHEDA" ((start . ((x . -206.048960112255) (y . 124.211835957643))) (end . ((x . -205.998413174569) (y . 124.241019245723)))))
  ("LINE" "CACEM - LINEE SCHEDA" ((start . ((x . -206.048960112255) (y . 124.328569109963))) (end . ((x . -206.048960112255) (y . 124.211835957643)))))
  ("LINE" "CACEM - LINEE SCHEDA" ((start . ((x . -205.897319299195) (y . 124.241019245723))) (end . ((x . -205.897319299195) (y . 124.124286093402)))))
  ("LINE" "CACEM - LINEE SCHEDA" ((start . ((x . -205.897319299195) (y . 124.202108194949))) (end . ((x . -205.998413174569) (y . 124.260474771109)))))
  ("LINE" "CACEM - LINEE SCHEDA" ((start . ((x . -205.897319299195) (y . 124.192380432255))) (end . ((x . -205.998413174569) (y . 124.250747008416)))))
  ("LINE" "CACEM - LINEE SCHEDA" ((start . ((x . -205.897319299195) (y . 124.211835957643))) (end . ((x . -205.998413174569) (y . 124.270202533803)))))
  ("LINE" "CACEM - LINEE SCHEDA" ((start . ((x . -205.947866236883) (y . 124.211835957643))) (end . ((x . -205.998413174569) (y . 124.241019245723)))))
  ("LINE" "CACEM - LINEE SCHEDA" ((start . ((x . -205.846772361509) (y . 124.211835957643))) (end . ((x . -205.796225423822) (y . 124.241019245723)))))
  ("LINE" "CACEM - LINEE SCHEDA" ((start . ((x . -216.384995254658) (y . 126.568071073293))) (end . ((x . -210.055177382935) (y . 126.568071073293)))))
  ("LWPOLYLINE" "CACEM - LINEE SCHEDA" ((vertices . (((x . -226.146309004019) (y . 121.493216363377)))) (bulges . ()) (closed . T)))
  ("LWPOLYLINE" "CACEM - LINEE SCHEDA" ((vertices . (((x . -216.384995254658) (y . 123.855819092686)))) (bulges . ()) (closed . T)))
  ("LINE" "CACEM - LINEE SCHEDA" ((start . ((x . -226.146309004019) (y . 123.058475170044))) (end . ((x . -221.160377436599) (y . 123.058475170044)))))
  ("LWPOLYLINE" "CACEM - LINEE SCHEDA" ((vertices . (((x . -216.384995254659) (y . 121.493216363377)))) (bulges . ()) (closed . T)))
  ("LWPOLYLINE" "CACEM - LINEE SCHEDA" ((vertices . (((x . -221.160377436599) (y . 123.497993912532)))) (bulges . ()) (closed . T)))
  ("LWPOLYLINE" "CACEM - LINEE SCHEDA" ((vertices . (((x . -221.045327181226) (y . 127.137806210646)))) (bulges . ()) (closed . T)))
  ("LWPOLYLINE" "CACEM - LINEE SCHEDA" ((vertices . (((x . -221.160377436599) (y . 125.552677069509)))) (bulges . ()) (closed . T)))
  ("LINE" "CACEM - LINEE SCHEDA" ((start . ((x . -212.295245497313) (y . 124.520427263746))) (end . ((x . -211.976301781443) (y . 124.839374009228)))))
  ("LINE" "CACEM - LINEE SCHEDA" ((start . ((x . -214.463870855101) (y . 124.520427263746))) (end . ((x . -214.14492713923) (y . 124.839374009228)))))
  ("LINE" "CACEM - LINEE SCHEDA" ((start . ((x . -216.058598523194) (y . 124.520427263746))) (end . ((x . -215.739654807324) (y . 124.839374009228)))))
  ("LINE" "CACEM - LINEE SCHEDA" ((start . ((x . -210.70051782922) (y . 124.520427263746))) (end . ((x . -210.381574113349) (y . 124.839374009228)))))
  ("LWPOLYLINE" "CACEM - LINEE SCHEDA" ((vertices . (((x . -226.226309004019) (y . 121.378166108004)))) (bulges . ()) (closed . T)))
  ("LWPOLYLINE" "CACEM - LINEE SCHEDA" ((vertices . (((x . -226.306426306179) (y . 121.298048805844)))) (bulges . ()) (closed . T)))
)))
    (setq *tnl7-holes* (list
  ( "INSERT-WORLD" "1__DOT" ((insertion . ((x . -220.157746980897) (y . 121.938390970767))) (rotation . 180) (scale_x . 0.0233577543257258) (scale_y . 0.0233577543257258) (world_geometry . ())))
  ("INSERT-WORLD" "1__DOT" ((insertion . ((x . -217.238027690177) (y . 121.938390970767))) (rotation . 0.0) (scale_x . 0.0233577543257258) (scale_y . 0.0233577543257258) (world_geometry . ())))
  ("INSERT-WORLD" "1__DOT" ((insertion . ((x . -220.157746980897) (y . 122.239443304381))) (rotation . 180) (scale_x . 0.0233577543257258) (scale_y . 0.0233577543257258) (world_geometry . ())))
  ("INSERT-WORLD" "1__DOT" ((insertion . ((x . -219.632197508567) (y . 122.239443304381))) (rotation . 0.0) (scale_x . 0.0233577543257258) (scale_y . 0.0233577543257258) (world_geometry . ())))
  ("INSERT-WORLD" "1__DOT" ((insertion . ((x . -219.632197508567) (y . 122.239443304381))) (rotation . 180) (scale_x . 0.0233577543257258) (scale_y . 0.0233577543257258) (world_geometry . ())))
  ("INSERT-WORLD" "1__DOT" ((insertion . ((x . -218.639492949723) (y . 122.239443304381))) (rotation . 0.0) (scale_x . 0.0233577543257258) (scale_y . 0.0233577543257258) (world_geometry . ())))
  ("INSERT-WORLD" "1__DOT" ((insertion . ((x . -218.639492949723) (y . 122.239443304381))) (rotation . 180) (scale_x . 0.0233577543257258) (scale_y . 0.0233577543257258) (world_geometry . ())))
  ("INSERT-WORLD" "1__DOT" ((insertion . ((x . -218.113943477393) (y . 122.239443304381))) (rotation . 0.0) (scale_x . 0.0233577543257258) (scale_y . 0.0233577543257258) (world_geometry . ())))
  ("INSERT-WORLD" "1__DOT" ((insertion . ((x . -218.113943477393) (y . 122.239443304381))) (rotation . 180) (scale_x . 0.0233577543257258) (scale_y . 0.0233577543257258) (world_geometry . ())))
  ("INSERT-WORLD" "1__DOT" ((insertion . ((x . -217.238027690177) (y . 122.239443304381))) (rotation . 0.0) (scale_x . 0.0233577543257258) (scale_y . 0.0233577543257258) (world_geometry . ())))
  ("INSERT-WORLD" "1__DOT" ((insertion . ((x . -220.157746980897) (y . 122.576678519046))) (rotation . 180) (scale_x . 0.0233577543257258) (scale_y . 0.0233577543257258) (world_geometry . ())))
  ("INSERT-WORLD" "1__DOT" ((insertion . ((x . -220.01176101636) (y . 122.576678519046))) (rotation . 180) (scale_x . 0.0233577543257258) (scale_y . 0.0233577543257258) (world_geometry . ())))
  ("INSERT-WORLD" "1__DOT" ((insertion . ((x . -219.865775051825) (y . 122.576678519046))) (rotation . 180) (scale_x . 0.0233577543257258) (scale_y . 0.0233577543257258) (world_geometry . ())))
  ("INSERT-WORLD" "1__DOT" ((insertion . ((x . -219.719789087288) (y . 122.576678519046))) (rotation . 180) (scale_x . 0.0233577543257258) (scale_y . 0.0233577543257258) (world_geometry . ())))
  ("INSERT-WORLD" "1__DOT" ((insertion . ((x . -219.573803122754) (y . 122.576678519046))) (rotation . 180) (scale_x . 0.0233577543257258) (scale_y . 0.0233577543257258) (world_geometry . ())))
  ("INSERT-WORLD" "1__DOT" ((insertion . ((x . -219.281831193681) (y . 122.576678519046))) (rotation . 180) (scale_x . 0.0233577543257258) (scale_y . 0.0233577543257258) (world_geometry . ())))
  ("INSERT-WORLD" "1__DOT" ((insertion . ((x . -219.135845229145) (y . 122.576678519046))) (rotation . 180) (scale_x . 0.0233577543257258) (scale_y . 0.0233577543257258) (world_geometry . ())))
  ("INSERT-WORLD" "1__DOT" ((insertion . ((x . -218.989859264609) (y . 122.576678519046))) (rotation . 180) (scale_x . 0.0233577543257258) (scale_y . 0.0233577543257258) (world_geometry . ())))
  ("INSERT-WORLD" "1__DOT" ((insertion . ((x . -218.697887335538) (y . 122.576678519046))) (rotation . 180) (scale_x . 0.0233577543257258) (scale_y . 0.0233577543257258) (world_geometry . ())))
  ("INSERT-WORLD" "1__DOT" ((insertion . ((x . -218.551901371002) (y . 122.576678519046))) (rotation . 180) (scale_x . 0.0233577543257258) (scale_y . 0.0233577543257258) (world_geometry . ())))
  ("INSERT-WORLD" "1__DOT" ((insertion . ((x . -218.405915406465) (y . 122.576678519046))) (rotation . 180) (scale_x . 0.0233577543257258) (scale_y . 0.0233577543257258) (world_geometry . ())))
  ("INSERT-WORLD" "1__DOT" ((insertion . ((x . -218.259929441929) (y . 122.576678519046))) (rotation . 180) (scale_x . 0.0233577543257258) (scale_y . 0.0233577543257258) (world_geometry . ())))
  ("INSERT-WORLD" "1__DOT" ((insertion . ((x . -218.113943477394) (y . 122.576678519046))) (rotation . 180) (scale_x . 0.0233577543257258) (scale_y . 0.0233577543257258) (world_geometry . ())))
  ("INSERT-WORLD" "1__DOT" ((insertion . ((x . -220.790942330333) (y . 122.777468425406))) (rotation . 270) (scale_x . 0.0233577543257258) (scale_y . 0.0233577543257258) (world_geometry . ())))
  ("INSERT-WORLD" "1__DOT" ((insertion . ((x . -220.493987120714) (y . 122.777468425406))) (rotation . 270) (scale_x . 0.0233577543257258) (scale_y . 0.0233577543257258) (world_geometry . ())))
  ("INSERT-WORLD" "1__DOT" ((insertion . ((x . -217.066197009499) (y . 122.777468425406))) (rotation . 270) (scale_x . 0.0233577543257258) (scale_y . 0.0233577543257258) (world_geometry . ())))
  ("INSERT-WORLD" "1__DOT" ((insertion . ((x . -216.716285067155) (y . 122.777468425406))) (rotation . 270) (scale_x . 0.0233577543257258) (scale_y . 0.0233577543257258) (world_geometry . ())))
  ("INSERT-WORLD" "1__DOT" ((insertion . ((x . -217.066197009499) (y . 122.923454389941))) (rotation . 270) (scale_x . 0.0233577543257258) (scale_y . 0.0233577543257258) (world_geometry . ())))
  ("INSERT-WORLD" "1__DOT" ((insertion . ((x . -217.066197009499) (y . 123.069440354478))) (rotation . 270) (scale_x . 0.0233577543257258) (scale_y . 0.0233577543257258) (world_geometry . ())))
  ("INSERT-WORLD" "1__DOT" ((insertion . ((x . -220.493987120714) (y . 123.273820704828))) (rotation . 90) (scale_x . 0.0233577543257258) (scale_y . 0.0233577543257258) (world_geometry . ())))
  ("INSERT-WORLD" "1__DOT" ((insertion . ((x . -220.493987120714) (y . 123.273820704828))) (rotation . 270) (scale_x . 0.0233577543257258) (scale_y . 0.0233577543257258) (world_geometry . ())))
  ("INSERT-WORLD" "1__DOT" ((insertion . ((x . -216.716285067155) (y . 123.361412283549))) (rotation . 90) (scale_x . 0.0233577543257258) (scale_y . 0.0233577543257258) (world_geometry . ())))
  ("INSERT-WORLD" "1__DOT" ((insertion . ((x . -216.716285067155) (y . 123.361412283549))) (rotation . 270) (scale_x . 0.0233577543257258) (scale_y . 0.0233577543257258) (world_geometry . ())))
  ("INSERT-WORLD" "1__DOT" ((insertion . ((x . -220.790942330333) (y . 125.11324385798))) (rotation . 90) (scale_x . 0.0233577543257258) (scale_y . 0.0233577543257258) (world_geometry . ())))
  ("INSERT-WORLD" "1__DOT" ((insertion . ((x . -220.493987120714) (y . 125.11324385798))) (rotation . 90) (scale_x . 0.0233577543257258) (scale_y . 0.0233577543257258) (world_geometry . ())))
  ("INSERT-WORLD" "1__DOT" ((insertion . ((x . -216.716285067155) (y . 125.11324385798))) (rotation . 90) (scale_x . 0.0233577543257258) (scale_y . 0.0233577543257258) (world_geometry . ())))
  ("INSERT-WORLD" "1__DOT" ((insertion . ((x . -219.69070160685) (y . 125.280303715955))) (rotation . 0.0) (scale_x . 0.0233577543257258) (scale_y . 0.0233577543257258) (world_geometry . ())))
  ("INSERT-WORLD" "1__DOT" ((insertion . ((x . -219.632197508567) (y . 125.280303715955))) (rotation . 180) (scale_x . 0.0233577543257258) (scale_y . 0.0233577543257258) (world_geometry . ())))
  ("INSERT-WORLD" "1__DOT" ((insertion . ((x . -218.639492949723) (y . 125.280303715955))) (rotation . 0.0) (scale_x . 0.0233577543257258) (scale_y . 0.0233577543257258) (world_geometry . ())))
  ("INSERT-WORLD" "1__DOT" ((insertion . ((x . -218.580988851441) (y . 125.280303715955))) (rotation . 180) (scale_x . 0.0233577543257258) (scale_y . 0.0233577543257258) (world_geometry . ())))
  ("INSERT-WORLD" "1__DOT" ((insertion . ((x . -220.157746980897) (y . 125.477335347242))) (rotation . 180) (scale_x . 0.0233577543257258) (scale_y . 0.0233577543257258) (world_geometry . ())))
  ("INSERT-WORLD" "1__DOT" ((insertion . ((x . -219.69070160685) (y . 125.477335347242))) (rotation . 0.0) (scale_x . 0.0233577543257258) (scale_y . 0.0233577543257258) (world_geometry . ())))
  ("INSERT-WORLD" "1__DOT" ((insertion . ((x . -219.69070160685) (y . 125.477335347242))) (rotation . 180) (scale_x . 0.0233577543257258) (scale_y . 0.0233577543257258) (world_geometry . ())))
  ("INSERT-WORLD" "1__DOT" ((insertion . ((x . -218.580988851441) (y . 125.477335347242))) (rotation . 180) (scale_x . 0.0233577543257258) (scale_y . 0.0233577543257258) (world_geometry . ())))
  ("INSERT-WORLD" "1__DOT" ((insertion . ((x . -218.580988851441) (y . 125.477335347242))) (rotation . 0.0) (scale_x . 0.0233577543257258) (scale_y . 0.0233577543257258) (world_geometry . ())))
  ("INSERT-WORLD" "1__DOT" ((insertion . ((x . -218.113943477394) (y . 125.477335347242))) (rotation . 0.0) (scale_x . 0.0233577543257258) (scale_y . 0.0233577543257258) (world_geometry . ())))
  ("INSERT-WORLD" "1__DOT" ((insertion . ((x . -220.157746980897) (y . 125.759435667193))) (rotation . 180) (scale_x . 0.0233577543257258) (scale_y . 0.0233577543257258) (world_geometry . ())))
  ("INSERT-WORLD" "1__DOT" ((insertion . ((x . -218.113943477394) (y . 125.759435667193))) (rotation . 0.0) (scale_x . 0.0233577543257258) (scale_y . 0.0233577543257258) (world_geometry . ())))
)))
    (setq *tnl7-reinforcement* (list
  ( "LWPOLYLINE" "CACEM - ARMATURA" ((vertices . ()) (bulges . ()) (closed . NIL)))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
  ("LWPOLYLINE" "CACEM - ARMATURA" ((vertices . ()) (bulges . ()) (closed . NIL)))
  ("LWPOLYLINE" "CACEM - ARMATURA" ((vertices . ()) (bulges . ()) (closed . NIL)))
  ("LWPOLYLINE" "CACEM - ARMATURA" ((vertices . ()) (bulges . ()) (closed . NIL)))
  ("LWPOLYLINE" "CACEM - ARMATURA" ((vertices . ()) (bulges . ()) (closed . NIL)))
  ("LWPOLYLINE" "CACEM - ARMATURA" ((vertices . ()) (bulges . ()) (closed . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
  ("CIRCLE" "CACEM - ARMATURA" ((center . ((x . NIL) (y . NIL))) (radius . NIL)))
  ("CIRCLE" "CACEM - ARMATURA" ((center . ((x . NIL) (y . NIL))) (radius . NIL)))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
  ("CIRCLE" "CACEM - ARMATURA" ((center . ((x . NIL) (y . NIL))) (radius . NIL)))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("CIRCLE" "CACEM - ARMATURA" ((center . ((x . NIL) (y . NIL))) (radius . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("ARC" "CACEM - ARMATURA" ((center . ((x . NIL) (y . NIL))) (radius . NIL) (start_angle . NIL) (end_angle . NIL)))
  ("ARC" "CACEM - ARMATURA" ((center . ((x . NIL) (y . NIL))) (radius . NIL) (start_angle . NIL) (end_angle . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
  ("LWPOLYLINE" "CACEM - ARMATURA" ((vertices . ()) (bulges . ()) (closed . NIL)))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LINE" "CACEM - ARMATURA" ((start . ((x . NIL) (y . NIL))) (end . ((x . NIL) (y . NIL)))))
  ("LWPOLYLINE" "CACEM - ARMATURA" ((vertices . ()) (bulges . ()) (closed . NIL)))
)))
    (setq *tnl7-halfens* (list
  ( "LINE" "CACEM - HALFEN" ((start . ((x . -212.161633353029) (y . 130.411788734793))) (end . ((x . -212.16163335303) (y . 130.154286518359)))))
  ("LINE" "CACEM - HALFEN" ((start . ((x . -211.854525398208) (y . 130.283037626585))) (end . ((x . -212.468741307849) (y . 130.283037626585)))))
  ("LINE" "CACEM - HALFEN" ((start . ((x . -214.711633352981) (y . 130.411788734793))) (end . ((x . -214.711633352981) (y . 130.154286518359)))))
  ("LINE" "CACEM - HALFEN" ((start . ((x . -214.40452539816) (y . 130.283037626585))) (end . ((x . -215.0187413078) (y . 130.283037626585)))))
  ("LINE" "CACEM - HALFEN" ((start . ((x . -209.611633353029) (y . 130.411788734793))) (end . ((x . -209.61163335303) (y . 130.154286518359)))))
  ("LINE" "CACEM - HALFEN" ((start . ((x . -209.304525398208) (y . 130.283037626585))) (end . ((x . -209.918741307849) (y . 130.283037626585)))))
)))
    (setq *tnl7-deha* (list
  ( "ARC" "CACEM - GANCI DEHA" ((center . ((x . -214.396633416367) (y . 135.61272435648))) (radius . 0.0705563282636059) (start_angle . 180) (end_angle . 0.0)))
  ("LINE" "CACEM - GANCI DEHA" ((start . ((x . -214.373828350791) (y . 135.608547918933))) (end . ((x . -214.419438355147) (y . 135.608547918933)))))
  ("LINE" "CACEM - GANCI DEHA" ((start . ((x . -214.373828350791) (y . 135.591444167299))) (end . ((x . -214.419438355147) (y . 135.591444167299)))))
  ("LINE" "CACEM - GANCI DEHA" ((start . ((x . -214.373828350791) (y . 135.608547918933))) (end . ((x . -214.373828350791) (y . 135.591444167299)))))
  ("LINE" "CACEM - GANCI DEHA" ((start . ((x . -214.419438355147) (y . 135.608547918933))) (end . ((x . -214.419438355147) (y . 135.591444167299)))))
  ("LINE" "CACEM - GANCI DEHA" ((start . ((x . -214.368127100246) (y . 135.444474472164))) (end . ((x . -214.368127100246) (y . 135.43877322162)))))
  ("LINE" "CACEM - GANCI DEHA" ((start . ((x . -214.408035854058) (y . 135.450175734123))) (end . ((x . -214.425139605692) (y . 135.444474483578)))))
  ("LINE" "CACEM - GANCI DEHA" ((start . ((x . -214.38523085188) (y . 135.450175722709))) (end . ((x . -214.408035854058) (y . 135.450175722709)))))
  ("LINE" "CACEM - GANCI DEHA" ((start . ((x . -214.425139605692) (y . 135.444474472164))) (end . ((x . -214.425139605692) (y . 135.43877322162)))))
  ("LINE" "CACEM - GANCI DEHA" ((start . ((x . -214.38523085188) (y . 135.450175734123))) (end . ((x . -214.368127100246) (y . 135.444474483578)))))
  ("LINE" "CACEM - GANCI DEHA" ((start . ((x . -214.368127100246) (y . 135.444474472164))) (end . ((x . -214.425139605692) (y . 135.444474472164)))))
  ("LINE" "CACEM - GANCI DEHA" ((start . ((x . -214.368127100246) (y . 135.43877322162))) (end . ((x . -214.425139605692) (y . 135.43877322162)))))
  ("LINE" "CACEM - GANCI DEHA" ((start . ((x . -214.408035854058) (y . 135.591444167299))) (end . ((x . -214.408035854058) (y . 135.450175734123)))))
  ("LINE" "CACEM - GANCI DEHA" ((start . ((x . -214.38523085188) (y . 135.591444167299))) (end . ((x . -214.38523085188) (y . 135.450175734123)))))
  ("ARC" "CACEM - GANCI DEHA" ((center . ((x . -209.141633416367) (y . 135.61272435648))) (radius . 0.0705563282636059) (start_angle . 180) (end_angle . 0.0)))
  ("LINE" "CACEM - GANCI DEHA" ((start . ((x . -209.118828350791) (y . 135.608547918932))) (end . ((x . -209.164438355147) (y . 135.608547918932)))))
  ("LINE" "CACEM - GANCI DEHA" ((start . ((x . -209.118828350791) (y . 135.591444167299))) (end . ((x . -209.164438355147) (y . 135.591444167299)))))
  ("LINE" "CACEM - GANCI DEHA" ((start . ((x . -209.118828350791) (y . 135.608547918932))) (end . ((x . -209.118828350791) (y . 135.591444167299)))))
  ("LINE" "CACEM - GANCI DEHA" ((start . ((x . -209.164438355147) (y . 135.608547918932))) (end . ((x . -209.164438355147) (y . 135.591444167299)))))
  ("LINE" "CACEM - GANCI DEHA" ((start . ((x . -209.113127100246) (y . 135.444474472164))) (end . ((x . -209.113127100246) (y . 135.438773221619)))))
  ("LINE" "CACEM - GANCI DEHA" ((start . ((x . -209.153035854058) (y . 135.450175734122))) (end . ((x . -209.170139605692) (y . 135.444474483578)))))
  ("LINE" "CACEM - GANCI DEHA" ((start . ((x . -209.13023085188) (y . 135.450175722708))) (end . ((x . -209.153035854058) (y . 135.450175722708)))))
  ("LINE" "CACEM - GANCI DEHA" ((start . ((x . -209.170139605692) (y . 135.444474472164))) (end . ((x . -209.170139605692) (y . 135.438773221619)))))
  ("LINE" "CACEM - GANCI DEHA" ((start . ((x . -209.13023085188) (y . 135.450175734122))) (end . ((x . -209.113127100246) (y . 135.444474483578)))))
  ("LINE" "CACEM - GANCI DEHA" ((start . ((x . -209.113127100246) (y . 135.444474472164))) (end . ((x . -209.170139605692) (y . 135.444474472164)))))
  ("LINE" "CACEM - GANCI DEHA" ((start . ((x . -209.113127100246) (y . 135.438773221619))) (end . ((x . -209.170139605692) (y . 135.438773221619)))))
  ("LINE" "CACEM - GANCI DEHA" ((start . ((x . -209.153035854058) (y . 135.591444167299))) (end . ((x . -209.153035854058) (y . 135.450175734122)))))
  ("LINE" "CACEM - GANCI DEHA" ((start . ((x . -209.13023085188) (y . 135.591444167299))) (end . ((x . -209.13023085188) (y . 135.450175734122)))))
  ("LWPOLYLINE" "CACEM - GANCI DEHA" ((vertices . (((x . -214.282768230183) (y . 134.898766977575)))) (bulges . (-0.99999999991553)) (closed . NIL)))
  ("LWPOLYLINE" "CACEM - GANCI DEHA" ((vertices . (((x . -209.255498475755) (y . 134.898766977575)))) (bulges . (0.99999999991553)) (closed . NIL)))
)))
    (setq *tnl7-strands* ())
    (setq *tnl7-mask* (list
  ( "LINE" "CACEM - PIASTRA POSIZIONE Y" ((start . ((x . -212.751633353009) (y . 129.163037626585))) (end . ((x . -212.751633353009) (y . 129.765030928331)))))
  ("LINE" "CACEM - TESTI" ((start . ((x . -223.944681004267) (y . 123.645897495619))) (end . ((x . -223.944681004267) (y . 123.674339497988)))))
  ("LINE" "CACEM - TESTI" ((start . ((x . -223.973120836644) (y . 123.702782585332))) (end . ((x . -223.8593528272) (y . 123.702782585332)))))
  ("ARC" "CACEM - TESTI" ((center . ((x . -223.973120836644) (y . 123.645897495619))) (radius . 0.0284424367826867) (start_angle . 270) (end_angle . 0.0)))
  ("ARC" "CACEM - TESTI" ((center . ((x . -223.973120836644) (y . 123.674339497988))) (radius . 0.0284424367826867) (start_angle . 0.0) (end_angle . 90)))
  ("ARC" "CACEM - TESTI" ((center . ((x . -224.058449013716) (y . 123.645897495619))) (radius . 0.0284424367826867) (start_angle . 180) (end_angle . 270)))
  ("ARC" "CACEM - TESTI" ((center . ((x . -224.058449013716) (y . 123.674339497988))) (radius . 0.0284424367826867) (start_angle . 90) (end_angle . 180)))
  ("LINE" "CACEM - TESTI" ((start . ((x . -224.086893186061) (y . 123.674339497988))) (end . ((x . -224.086893186061) (y . 123.645897495619)))))
  ("LINE" "CACEM - TESTI" ((start . ((x . -223.973120836644) (y . 123.702782585332))) (end . ((x . -224.058449013716) (y . 123.702782585332)))))
  ("LINE" "CACEM - TESTI" ((start . ((x . -224.058449013716) (y . 123.617455058837))) (end . ((x . -223.971106038463) (y . 123.617455058837)))))
  ("LINE" "CACEM - TESTI" ((start . ((x . -223.445647061387) (y . 123.602853843738))) (end . ((x . -223.52413169656) (y . 123.560273321491)))))
  ("LINE" "CACEM - TESTI" ((start . ((x . -223.521996048456) (y . 123.860376937194))) (end . ((x . -223.598670226638) (y . 123.818778648017)))))
  ("LINE" "CACEM - TESTI" ((start . ((x . -223.504634860444) (y . 124.628948985552))) (end . ((x . -223.581309038626) (y . 124.587350696376)))))
  ("LINE" "CACEM - TESTI" ((start . ((x . -223.504634860444) (y . 124.145846555155))) (end . ((x . -223.581309038626) (y . 124.104248265978)))))
  ("LINE" "CACEM - TESTI" ((start . ((x . -223.504634860444) (y . 124.37641816966))) (end . ((x . -223.581309038626) (y . 124.334819880483)))))
  ("LWPOLYLINE" "CACEM - TESTI" ((vertices . (((x . -215.650641217541) (y . 122.379041820175)))) (bulges . ()) (closed . NIL)))
  ("LWPOLYLINE" "CACEM - TESTI" ((vertices . (((x . -215.394911345031) (y . 122.634771692688)))) (bulges . ()) (closed . NIL)))
  ("LINE" "CACEM - TESTI" ((start . ((x . -208.533633352969) (y . 135.261697816318))) (end . ((x . -208.303081960711) (y . 135.261697816318)))))
  ("LINE" "CACEM - TESTI" ((start . ((x . -208.533633352969) (y . 135.261697816318))) (end . ((x . -208.44110663352) (y . 135.246816212666)))))
  ("CIRCLE" "CACEM - TESTI" ((center . ((x . -208.190328507615) (y . 135.258511213228))) (radius . 0.112798473500678)))
  ("CIRCLE" "CACEM - TESTI" ((center . ((x . -208.152865878857) (y . 135.896598525199))) (radius . 0.159703928215218)))
  ("CIRCLE" "CACEM - TESTI" ((center . ((x . -215.501155765915) (y . 135.863264300639))) (radius . 0.159703928215218)))
  ("LINE" "CACEM - TESTI" ((start . ((x . -210.743190443422) (y . 134.85472435648))) (end . ((x . -210.760820887056) (y . 134.745106660019)))))
  ("CIRCLE" "CACEM - TESTI" ((center . ((x . -210.746377046512) (y . 134.535563061592))) (radius . 0.112798473500678)))
  ("LINE" "CACEM - TESTI" ((start . ((x . -210.743190443422) (y . 134.85472435648))) (end . ((x . -210.743190443422) (y . 134.648316514687)))))
  ("CIRCLE" "CACEM - TESTI" ((center . ((x . -211.255551348265) (y . 134.588796452138))) (radius . 0.112798473500678)))
  ("LINE" "CACEM - TESTI" ((start . ((x . -211.252364745176) (y . 135.368724356479))) (end . ((x . -211.252364745176) (y . 134.701549905233)))))
  ("LINE" "CACEM - TESTI" ((start . ((x . -211.252364745176) (y . 134.936038064979))) (end . ((x . -211.26999518881) (y . 134.826420368517)))))
  ("LINE" "CACEM - TESTI" ((start . ((x . -211.252364745176) (y . 134.995493919653))) (end . ((x . -211.26999518881) (y . 134.885876223192)))))
  ("LINE" "CACEM - TESTI" ((start . ((x . -211.252364745176) (y . 135.16272435648))) (end . ((x . -211.26999518881) (y . 135.053106660019)))))
  ("LINE" "CACEM - TESTI" ((start . ((x . -211.252364745176) (y . 135.368724356479))) (end . ((x . -211.26999518881) (y . 135.259106660019)))))
  ("LINE" "CACEM - TESTI" ((start . ((x . -210.535457433773) (y . 135.562140133505))) (end . ((x . -210.552762278567) (y . 135.669733411545)))))
  ("LINE" "CACEM - TESTI" ((start . ((x . -210.535457433773) (y . 135.562140133505))) (end . ((x . -210.535457433773) (y . 135.868320951186)))))
  ("CIRCLE" "CACEM - TESTI" ((center . ((x . -210.538644036863) (y . 135.981074404281))) (radius . 0.112798473500678)))
  ("LINE" "CACEM - TESTI" ((start . ((x . -214.538418575605) (y . 134.888724356479))) (end . ((x . -214.556049019239) (y . 134.779106660018)))))
  ("CIRCLE" "CACEM - TESTI" ((center . ((x . -214.541605178695) (y . 134.535563061591))) (radius . 0.112798473500678)))
  ("LINE" "CACEM - TESTI" ((start . ((x . -214.538418575605) (y . 134.888724356479))) (end . ((x . -214.538418575605) (y . 134.648316514686)))))
  ("LINE" "CACEM - PIASTRA POSIZIONE Y" ((start . ((x . -212.80163335301) (y . 129.563037626585))) (end . ((x . -212.80163335301) (y . 129.463037626585)))))
  ("LINE" "CACEM - PIASTRA POSIZIONE Y" ((start . ((x . -212.701633353009) (y . 129.563037626585))) (end . ((x . -212.701633353009) (y . 129.463037626585)))))
  ("LINE" "CACEM - PIASTRA POSIZIONE Y" ((start . ((x . -212.886900480621) (y . 129.513037626585))) (end . ((x . -212.616366225398) (y . 129.513037626585)))))
  ("LINE" "CACEM - PIASTRA POSIZIONE Y" ((start . ((x . -212.80163335301) (y . 129.563037626585))) (end . ((x . -212.701633353009) (y . 129.563037626585)))))
  ("LINE" "CACEM - PIASTRA POSIZIONE Y" ((start . ((x . -212.80163335301) (y . 129.463037626585))) (end . ((x . -212.701633353009) (y . 129.463037626585)))))
  ("LINE" "CACEM - TESTI" ((start . ((x . -220.699001226661) (y . 136.259255524565))) (end . ((x . -220.221582013103) (y . 136.259255524565)))))
  ("LINE" "CACEM - TESTI" ((start . ((x . -220.386233113347) (y . 136.259255524565))) (end . ((x . -220.386233113347) (y . 136.155717725008)))))
  ("CIRCLE" "CACEM - TESTI" ((center . ((x . -220.848900501834) (y . 136.253759407531))) (radius . 0.150000000000002)))
  ("LINE" "CACEM - TESTI" ((start . ((x . -220.221582013103) (y . 136.259255524565))) (end . ((x . -220.221582013103) (y . 136.147519236396)))))
  ("CIRCLE" "CACEM - TESTI" ((center . ((x . -220.895915419953) (y . 135.402005936631))) (radius . 0.150000000000002)))
  ("LINE" "CACEM - TESTI" ((start . ((x . -220.74648867212) (y . 135.388904523278))) (end . ((x . -220.582706783625) (y . 135.388904523278)))))
  ("CIRCLE" "CACEM - TESTI" ((center . ((x . -220.895915419953) (y . 134.784005936631))) (radius . 0.150000000000002)))
  ("LINE" "CACEM - TESTI" ((start . ((x . -220.74648867212) (y . 134.770904523278))) (end . ((x . -220.582706783625) (y . 134.770904523278)))))
  ("CIRCLE" "CACEM - TESTI" ((center . ((x . -220.895915419953) (y . 134.103947062128))) (radius . 0.150000000000002)))
  ("LINE" "CACEM - TESTI" ((start . ((x . -220.74648867212) (y . 134.090845648775))) (end . ((x . -220.582706783625) (y . 134.090845648775)))))
  ("LINE" "CACEM - TESTI" ((start . ((x . -220.677194588411) (y . 133.418998563528))) (end . ((x . -220.315907563225) (y . 133.418998563528)))))
  ("CIRCLE" "CACEM - TESTI" ((center . ((x . -220.827014069719) (y . 133.411641728587))) (radius . 0.150000000000002)))
  ("LINE" "CACEM - TESTI" ((start . ((x . -220.315907563225) (y . 133.418998563528))) (end . ((x . -220.315907563225) (y . 133.674773234723)))))
  ("LINE" "CACEM - TESTI" ((start . ((x . -218.370910247068) (y . 133.516112701234))) (end . ((x . -218.831972525344) (y . 133.516112701233)))))
  ("CIRCLE" "CACEM - TESTI" ((center . ((x . -218.22109076576) (y . 133.508755866292))) (radius . 0.150000000000002)))
  ("LINE" "CACEM - TESTI" ((start . ((x . -218.607321425101) (y . 133.516112701233))) (end . ((x . -218.607321425101) (y . 133.674773234723)))))
  ("LINE" "CACEM - TESTI" ((start . ((x . -218.831972525344) (y . 133.516112701233))) (end . ((x . -218.831972525344) (y . 133.674773234723)))))
  ("CIRCLE" "CACEM - TESTI" ((center . ((x . -219.232611735824) (y . 133.381525249594))) (radius . 0.150000000000002)))
  ("LINE" "CACEM - TESTI" ((start . ((x . -219.522066051606) (y . 133.921904523278))) (end . ((x . -219.522066051606) (y . 133.37615395798)))))
  ("LINE" "CACEM - TESTI" ((start . ((x . -219.522066051606) (y . 133.37615395798))) (end . ((x . -219.382515535731) (y . 133.37615395798)))))
  ("LINE" "CACEM - TESTI" ((start . ((x . -219.522066051606) (y . 133.921904523278))) (end . ((x . -219.554993939327) (y . 133.75958868048)))))
  ("CIRCLE" "CACEM - TESTI" ((center . ((x . -217.912626899272) (y . 135.173330033543))) (radius . 0.150000000000002)))
  ("LINE" "CACEM - TESTI" ((start . ((x . -218.062073526944) (y . 135.186202697512))) (end . ((x . -218.536777269223) (y . 135.186202697512)))))
  ("LINE" "CACEM - TESTI" ((start . ((x . -218.536777269223) (y . 135.186202697512))) (end . ((x . -218.397283753309) (y . 135.209150929289)))))
  ("CIRCLE" "CACEM - TESTI" ((center . ((x . -219.766185546247) (y . 134.554837840345))) (radius . 0.150000000000002)))
  ("LINE" "CACEM - TESTI" ((start . ((x . -219.61628174634) (y . 134.549466548731))) (end . ((x . -219.390707234022) (y . 134.549466548731)))))
  ("LINE" "CACEM - TESTI" ((start . ((x . -219.390707234022) (y . 134.152904523278))) (end . ((x . -219.390707234022) (y . 134.549466548731)))))
  ("LINE" "CACEM - TESTI" ((start . ((x . -219.390707234022) (y . 134.152904523278))) (end . ((x . -219.410345535932) (y . 134.260011846308)))))
  ("LINE" "CACEM - TESTI" ((start . ((x . -220.69900122666) (y . 131.120591051205))) (end . ((x . -220.221582013103) (y . 131.120591051205)))))
  ("LINE" "CACEM - TESTI" ((start . ((x . -220.386233113347) (y . 131.120591051205))) (end . ((x . -220.386233113347) (y . 131.017053251647)))))
  ("CIRCLE" "CACEM - TESTI" ((center . ((x . -220.848900501834) (y . 131.115094934171))) (radius . 0.150000000000002)))
  ("LINE" "CACEM - TESTI" ((start . ((x . -220.221582013103) (y . 131.120591051205))) (end . ((x . -220.221582013103) (y . 131.008854763035)))))
  ("CIRCLE" "CACEM - TESTI" ((center . ((x . -220.879619288875) (y . 130.26334146327))) (radius . 0.150000000000002)))
  ("LINE" "CACEM - TESTI" ((start . ((x . -220.730192541041) (y . 130.250240049917))) (end . ((x . -220.582706783625) (y . 130.250240049917)))))
  ("CIRCLE" "CACEM - TESTI" ((center . ((x . -220.879619288875) (y . 129.64534146327))) (radius . 0.150000000000002)))
  ("LINE" "CACEM - TESTI" ((start . ((x . -220.730192541041) (y . 129.632240049917))) (end . ((x . -220.582706783625) (y . 129.632240049917)))))
  ("CIRCLE" "CACEM - TESTI" ((center . ((x . -220.879619288875) (y . 128.965282588767))) (radius . 0.150000000000002)))
  ("LINE" "CACEM - TESTI" ((start . ((x . -220.730192541041) (y . 128.952181175414))) (end . ((x . -220.582706783625) (y . 128.952181175414)))))
  ("LINE" "CACEM - TESTI" ((start . ((x . -218.607321425101) (y . 128.377448227873))) (end . ((x . -218.607321425101) (y . 128.536108761363)))))
  ("LINE" "CACEM - TESTI" ((start . ((x . -218.831972525344) (y . 128.377448227873))) (end . ((x . -218.831972525344) (y . 128.536108761363)))))
  ("CIRCLE" "CACEM - TESTI" ((center . ((x . -217.912626899272) (y . 130.034665560183))) (radius . 0.150000000000002)))
  ("LINE" "CACEM - TESTI" ((start . ((x . -218.062073526944) (y . 130.047538224151))) (end . ((x . -218.536777269223) (y . 130.047538224151)))))
  ("LINE" "CACEM - TESTI" ((start . ((x . -218.536777269223) (y . 130.047538224151))) (end . ((x . -218.397283753309) (y . 130.070486455928)))))
  ("LINE" "CACEM - TESTI" ((start . ((x . -219.560394400469) (y . 129.41080207537))) (end . ((x . -219.390707234022) (y . 129.41080207537)))))
  ("LINE" "CACEM - TESTI" ((start . ((x . -219.390707234022) (y . 129.014240049917))) (end . ((x . -219.390707234022) (y . 129.41080207537)))))
  ("LINE" "CACEM - TESTI" ((start . ((x . -219.390707234022) (y . 129.014240049917))) (end . ((x . -219.410345535932) (y . 129.121347372947)))))
  ("LINE" "CACEM - TESTI" ((start . ((x . -218.607321425101) (y . 128.377448227873))) (end . ((x . -218.974574130436) (y . 128.377448227872)))))
  ("CIRCLE" "CACEM - TESTI" ((center . ((x . -219.124393611745) (y . 128.370091392932))) (radius . 0.150000000000002)))
  ("LINE" "CACEM - TESTI" ((start . ((x . -218.310199806643) (y . 134.206288062782))) (end . ((x . -217.844470707533) (y . 133.418907491382)))))
  ("LINE" "CACEM - TESTI" ((start . ((x . -217.844470707533) (y . 133.418907491382))) (end . ((x . -217.69255683503) (y . 133.882248671987)))))
  ("LINE" "CACEM - TESTI" ((start . ((x . -217.707997909319) (y . 134.21400359291))) (end . ((x . -217.844470707533) (y . 133.418907491382)))))
  ("CIRCLE" "CACEM - TESTI" ((center . ((x . -217.844470707533) (y . 133.268907491382))) (radius . 0.150000000000002)))
  ("LINE" "CACEM - TESTI" ((start . ((x . -218.310199806644) (y . 129.067623589421))) (end . ((x . -217.844470707533) (y . 128.280243018021)))))
  ("LINE" "CACEM - TESTI" ((start . ((x . -217.844470707533) (y . 128.280243018021))) (end . ((x . -217.69255683503) (y . 128.743584198626)))))
  ("LINE" "CACEM - TESTI" ((start . ((x . -217.707997909319) (y . 129.075339119548))) (end . ((x . -217.844470707533) (y . 128.280243018021)))))
  ("CIRCLE" "CACEM - TESTI" ((center . ((x . -217.844470707533) (y . 128.130243018021))) (radius . 0.150000000000002)))
  ("CIRCLE" "CACEM - TESTI" ((center . ((x . -219.564621613145) (y . 128.292737245913))) (radius . 0.150000000000002)))
  ("LINE" "CACEM - TESTI" ((start . ((x . -219.826130170488) (y . 128.684240049917))) (end . ((x . -219.826130170488) (y . 128.287365954299)))))
  ("LINE" "CACEM - TESTI" ((start . ((x . -219.826130170488) (y . 128.287365954299))) (end . ((x . -219.714525413052) (y . 128.287365954299)))))
  ("LINE" "CACEM - TESTI" ((start . ((x . -219.826130170488) (y . 128.684240049917))) (end . ((x . -219.859058058208) (y . 128.521924207119)))))
  ("CIRCLE" "CACEM - TESTI" ((center . ((x . -219.835526359927) (y . 133.431401719274))) (radius . 0.150000000000002)))
  ("LINE" "CACEM - TESTI" ((start . ((x . -220.097034917269) (y . 133.822904523278))) (end . ((x . -220.097034917269) (y . 133.42603042766)))))
  ("LINE" "CACEM - TESTI" ((start . ((x . -220.097034917269) (y . 133.42603042766))) (end . ((x . -219.985430159833) (y . 133.42603042766)))))
  ("LINE" "CACEM - TESTI" ((start . ((x . -220.097034917269) (y . 133.822904523278))) (end . ((x . -220.129962804991) (y . 133.660588680479)))))
  ("CIRCLE" "CACEM - TESTI" ((center . ((x . -219.710298200375) (y . 129.416173366985))) (radius . 0.150000000000002)))
  ("LINE" "CACEM - TESTI" ((start . ((x . -218.082637581288) (y . 129.545802075371))) (end . ((x . -217.909423699016) (y . 129.545802075371)))))
  ("LINE" "CACEM - TESTI" ((start . ((x . -218.082637581288) (y . 129.149240049917))) (end . ((x . -218.082637581288) (y . 129.545802075371)))))
  ("LINE" "CACEM - TESTI" ((start . ((x . -218.082637581288) (y . 129.149240049917))) (end . ((x . -218.102275883197) (y . 129.256347372948)))))
  ("CIRCLE" "CACEM - TESTI" ((center . ((x . -217.759519899109) (y . 129.551173366985))) (radius . 0.150000000000002)))
  ("CIRCLE" "CACEM - TESTI" ((center . ((x . -217.912626899272) (y . 134.55879702965))) (radius . 0.150000000000002)))
  ("LINE" "CACEM - TESTI" ((start . ((x . -218.062073526944) (y . 134.571669693619))) (end . ((x . -218.668859124905) (y . 134.571669693619)))))
  ("LINE" "CACEM - TESTI" ((start . ((x . -218.668859124905) (y . 134.571669693619))) (end . ((x . -218.529365608991) (y . 134.594617925396)))))
  ("LINE" "CACEM - TESTI" ((start . ((x . -215.00463335297) (y . 135.261697816318))) (end . ((x . -215.235184745228) (y . 135.261697816318)))))
  ("LINE" "CACEM - TESTI" ((start . ((x . -215.00463335297) (y . 135.261697816318))) (end . ((x . -215.097160072419) (y . 135.246816212666)))))
  ("CIRCLE" "CACEM - TESTI" ((center . ((x . -215.347938198324) (y . 135.258511213228))) (radius . 0.112798473500678)))
  ("LWPOLYLINE" "CACEM - TESTI" ((vertices . (((x . -211.911633353029) (y . 130.268037626585)))) (bulges . ()) (closed . T)))
  ("LINE" "CACEM - PIASTRA POSIZIONE Y" ((start . ((x . -209.201633353009) (y . 129.163037626585))) (end . ((x . -209.201633353009) (y . 129.765030928331)))))
  ("LINE" "CACEM - PIASTRA POSIZIONE Y" ((start . ((x . -209.25163335301) (y . 129.563037626585))) (end . ((x . -209.25163335301) (y . 129.463037626585)))))
  ("LINE" "CACEM - PIASTRA POSIZIONE Y" ((start . ((x . -209.151633353009) (y . 129.563037626585))) (end . ((x . -209.151633353009) (y . 129.463037626585)))))
  ("LINE" "CACEM - PIASTRA POSIZIONE Y" ((start . ((x . -209.336900480621) (y . 129.513037626585))) (end . ((x . -209.066366225398) (y . 129.513037626585)))))
  ("LINE" "CACEM - PIASTRA POSIZIONE Y" ((start . ((x . -209.25163335301) (y . 129.563037626585))) (end . ((x . -209.151633353009) (y . 129.563037626585)))))
  ("LINE" "CACEM - PIASTRA POSIZIONE Y" ((start . ((x . -209.25163335301) (y . 129.463037626585))) (end . ((x . -209.151633353009) (y . 129.463037626585)))))
  ("LWPOLYLINE" "CACEM - TESTI" ((vertices . (((x . -214.461633352981) (y . 130.268037626585)))) (bulges . ()) (closed . T)))
  ("LWPOLYLINE" "CACEM - TESTI" ((vertices . (((x . -209.361633353029) (y . 130.268037626585)))) (bulges . ()) (closed . T)))
)))
    (setq *tnl7-dimensions* (list
  ( "DIMENSION" "CACEM-QUOTE" ((value . 657.500000000027) (point1 . ((x . -208.481633352969) (y . 127.922379930772))) (point2 . ((x . -211.769133352969) (y . 128.047379930772))) (text_position . ((x . -215.056633352969) (y . 128.641446070529))) (text . "657.5000000000272")))
  ("DIMENSION" "CACEM-QUOTE" ((value . 230.49999999605) (point1 . ((x . -215.05663335297) (y . 128.661446070529))) (point2 . ((x . -213.90413335299) (y . 128.733958373679))) (text_position . ((x . -212.751633353009) (y . 129.163037626585))) (text . "230.4999999960501")))
  ("DIMENSION" "CACEM-QUOTE" ((value . 657.500000000005) (point1 . ((x . -208.481633352969) (y . 133.301351642059))) (point2 . ((x . -211.769133352969) (y . 133.426351642059))) (text_position . ((x . -215.056633352969) (y . 133.945768000153))) (text . "657.5000000000045")))
  ("DIMENSION" "CACEM-QUOTE" ((value . 230.499999996073) (point1 . ((x . -212.751633353009) (y . 136.228696957714))) (point2 . ((x . -213.90413335299) (y . 136.301209260864))) (text_position . ((x . -215.05663335297) (y . 135.990832062303))) (text . "230.4999999960728")))
  ("DIMENSION" "CACEM-QUOTE" ((value . 149.999999999977) (point1 . ((x . -213.55663335297) (y . 133.91115146145))) (point2 . ((x . -214.30663335297) (y . 133.98365146145))) (text_position . ((x . -215.05663335297) (y . 134.584576767483))) (text . "149.9999999999771")))
  ("DIMENSION" "CACEM-QUOTE" ((value . 150) (point1 . ((x . -208.481633352969) (y . 133.911151461449))) (point2 . ((x . -209.231633352969) (y . 133.98365146145))) (text_position . ((x . -209.981633352969) (y . 134.584007566814))) (text . "150.0")))
  ("DIMENSION" "CACEM-QUOTE" ((value . 1040) (point1 . ((x . -208.481633352969) (y . 130.906014905198))) (point2 . ((x . -208.308302655617) (y . 130.976014905198))) (text_position . ((x . -208.676633352969) (y . 130.526607037181))) (text . "1040.0")))
  ("DIMENSION" "CACEM-QUOTE" ((value . 80.0000000000182) (point1 . ((x . -215.690565535261) (y . 134.812724356479))) (point2 . ((x . -215.815565535261) (y . 135.21272435648))) (text_position . ((x . -215.170707147468) (y . 135.61272435648))) (text . "80.00000000001818")))
  ("DIMENSION" "CACEM-QUOTE" ((value . 1040) (point1 . ((x . -207.869729707907) (y . 129.363037626585))) (point2 . ((x . -207.939729707907) (y . 129.513037626585))) (text_position . ((x . -208.481633352969) (y . 129.663037626585))) (text . "1040.0")))
  ("DIMENSION" "CACEM-QUOTE" ((value . 1040) (point1 . ((x . -207.869729707905) (y . 129.913037626585))) (point2 . ((x . -207.939741518929) (y . 129.788037626585))) (text_position . ((x . -208.481633352969) (y . 129.663037626585))) (text . "1040.0")))
  ("DIMENSION" "CACEM-QUOTE" ((value . 1040) (point1 . ((x . -207.869729707903) (y . 130.113037626585))) (point2 . ((x . -207.939741518927) (y . 130.013037626585))) (text_position . ((x . -208.481633352969) (y . 129.913037626585))) (text . "1040.0")))
  ("DIMENSION" "CACEM-QUOTE" ((value . 1040) (point1 . ((x . -207.869729707902) (y . 130.363037626585))) (point2 . ((x . -207.939741518926) (y . 130.238037626585))) (text_position . ((x . -208.481633352969) (y . 130.113037626585))) (text . "1040.0")))
  ("DIMENSION" "CACEM-QUOTE" ((value . 1040) (point1 . ((x . -207.481108217576) (y . 130.013037626585))) (point2 . ((x . -207.551108217576) (y . 129.688037626585))) (text_position . ((x . -207.84972970795) (y . 129.363037626585))) (text . "1040.0")))
  ("DIMENSION" "CACEM-QUOTE" ((value . 1040) (point1 . ((x . -207.481108217575) (y . 130.363037626585))) (point2 . ((x . -207.551108217575) (y . 130.188037626585))) (text_position . ((x . -207.849729707947) (y . 130.013037626585))) (text . "1040.0")))
  ("DIMENSION" "CACEM-QUOTE" ((value . 1040) (point1 . ((x . -215.587090350083) (y . 129.363037626585))) (point2 . ((x . -215.657090350083) (y . 129.513037626585))) (text_position . ((x . -215.05663335297) (y . 129.663037626585))) (text . "1040.0")))
  ("DIMENSION" "CACEM-QUOTE" ((value . 1040) (point1 . ((x . -215.587090350084) (y . 129.913037626585))) (point2 . ((x . -215.657102161108) (y . 129.788037626585))) (text_position . ((x . -215.05663335297) (y . 129.663037626585))) (text . "1040.0")))
  ("DIMENSION" "CACEM-QUOTE" ((value . 1040) (point1 . ((x . -215.587090350086) (y . 130.113037626585))) (point2 . ((x . -215.65710216111) (y . 130.013037626585))) (text_position . ((x . -215.05663335297) (y . 129.913037626585))) (text . "1040.0")))
  ("DIMENSION" "CACEM-QUOTE" ((value . 1040) (point1 . ((x . -215.587090350087) (y . 130.363037626585))) (point2 . ((x . -215.657102161111) (y . 130.238037626585))) (text_position . ((x . -215.05663335297) (y . 130.113037626585))) (text . "1040.0")))
  ("DIMENSION" "CACEM-QUOTE" ((value . 1040) (point1 . ((x . -215.970957569877) (y . 130.013037626585))) (point2 . ((x . -216.040957569877) (y . 129.688037626585))) (text_position . ((x . -215.607090350112) (y . 129.363037626585))) (text . "1040.0")))
  ("DIMENSION" "CACEM-QUOTE" ((value . 1040) (point1 . ((x . -215.970957569878) (y . 130.363037626585))) (point2 . ((x . -216.040957569878) (y . 130.188037626585))) (text_position . ((x . -215.607090350115) (y . 130.013037626585))) (text . "1040.0")))
  ("DIMENSION" "CACEM-QUOTE" ((value . 72.0000000040955) (point1 . ((x . -208.481633352969) (y . 128.661446070529))) (point2 . ((x . -208.84163335299) (y . 128.733958373679))) (text_position . ((x . -209.20163335301) (y . 129.103497229739))) (text . "72.00000000409545")))
  ("DIMENSION" "CACEM-QUOTE" ((value . 72.0000000040272) (point1 . ((x . -208.481633352969) (y . 136.228696957714))) (point2 . ((x . -208.841633352989) (y . 136.301209260864))) (text_position . ((x . -209.201633353009) (y . 135.997608710583))) (text . "72.00000000402723")))
  ("DIMENSION" "CACEM-QUOTE" ((value . 66.0000000000423) (point1 . ((x . -214.396633352969) (y . 135.806480669626))) (point2 . ((x . -214.726633352969) (y . 135.878980669626))) (text_position . ((x . -215.05663335297) (y . 135.61272435648))) (text . "66.00000000004229")))
  ("DIMENSION" "CACEM-QUOTE" ((value . 65.9999999999968) (point1 . ((x . -209.141633352969) (y . 135.806480669626))) (point2 . ((x . -208.811633352969) (y . 135.878980669626))) (text_position . ((x . -208.481633352969) (y . 135.61272435648))) (text . "65.99999999999682")))
  ("DIMENSION" "CACEM-QUOTE" ((value . 1040) (point1 . ((x . -215.05663335297) (y . 130.906014905198))) (point2 . ((x . -215.229964050322) (y . 130.976014905198))) (text_position . ((x . -214.86163335297) (y . 130.526607037181))) (text . "1040.0")))
  ("DIMENSION" "CACEM-QUOTE" ((value . 34.4999999939546) (point1 . ((x . -215.056633352969) (y . 131.258522352739))) (point2 . ((x . -214.884133353) (y . 131.331022352739))) (text_position . ((x . -214.71163335303) (y . 130.981245085555))) (text . "34.49999999395459")))
  ("DIMENSION" "CACEM-QUOTE" ((value . 254.999999999995) (point1 . ((x . -212.16163335303) (y . 131.258522352738))) (point2 . ((x . -213.43663335303) (y . 131.331034655888))) (text_position . ((x . -214.71163335303) (y . 130.998217897391))) (text . "254.9999999999954")))
  ("DIMENSION" "CACEM-QUOTE" ((value . 355.000000000018) (point1 . ((x . -209.201633353009) (y . 128.661446070529))) (point2 . ((x . -210.976633353009) (y . 128.733946070529))) (text_position . ((x . -212.751633353009) (y . 129.163037626585))) (text . "355.0000000000181")))
  ("DIMENSION" "CACEM-QUOTE" ((value . 120.000000000027) (point1 . ((x . -212.151633353009) (y . 133.91115146145))) (point2 . ((x . -212.751633353009) (y . 133.9836637646))) (text_position . ((x . -213.35163335301) (y . 134.584562233068))) (text . "120.0000000000273")))
  ("DIMENSION" "CACEM-QUOTE" ((value . 354.999999999973) (point1 . ((x . -209.201633353009) (y . 136.228696957714))) (point2 . ((x . -210.976633353009) (y . 136.301196957714))) (text_position . ((x . -212.751633353009) (y . 135.990832062303))) (text . "354.9999999999727")))
  ("DIMENSION" "CACEM-QUOTE" ((value . 217.000000004032) (point1 . ((x . -209.981633352969) (y . 133.91115146145))) (point2 . ((x . -211.066633352989) (y . 133.983663764599))) (text_position . ((x . -212.151633353009) (y . 134.440580577974))) (text . "217.0000000040318")))
  ("DIMENSION" "CACEM-QUOTE" ((value . 113.000000006036) (point1 . ((x . -209.61163335303) (y . 131.258522352739))) (point2 . ((x . -209.046633352999) (y . 131.331022352739))) (text_position . ((x . -208.481633352969) (y . 131.144635038976))) (text . "113.0000000060363")))
  ("DIMENSION" "CACEM-QUOTE" ((value . 255.000000000041) (point1 . ((x . -209.61163335303) (y . 131.258522352739))) (point2 . ((x . -210.88663335303) (y . 131.331034655889))) (text_position . ((x . -212.16163335303) (y . 130.882520404438))) (text . "255.0000000000409")))
  ("DIMENSION" "CACEM-QUOTE" ((value . 20.4999999960364) (point1 . ((x . -213.55663335297) (y . 133.91115146145))) (point2 . ((x . -213.45413335299) (y . 133.983663764599))) (text_position . ((x . -213.35163335301) (y . 134.440580577974))) (text . "20.49999999603642")))
)))
    (setq *tnl7-texts* (list
  ( "TEXT" "CACEM - TESTI" ((content . "GANCIO DEHA") (position . ((x . -214.362705733482) (y . 135.772841976763))) (height . 0.08) (rotation . 0.0)))
  ("MTEXT" "CACEM - TESTI" ((content . "44") (position . ((x . -214.758501504445) (y . 130.995336464483))) (height . 0.12) (rotation . 0.0)))
  ("MTEXT" "CACEM - TESTI" ((content . "44") (position . ((x . -214.257002970073) (y . 130.834169693774))) (height . 0.12) (rotation . 0.0)))
  ("TEXT" "CACEM - TESTI" ((content . "11") (position . ((x . -211.857042983359) (y . 129.49934881892))) (height . 0.0988216761064075) (rotation . 0.0)))
  ("TEXT" "CACEM - TESTI" ((content . "72") (position . ((x . -221.585315061556) (y . 134.924595434632))) (height . 0.0974217639170123) (rotation . 0.0)))
  ("TEXT" "CACEM - TESTI" ((content . "CARPENTERIA  VISTA IN PIANTA") (position . ((x . -216.334863878695) (y . 131.755479282423))) (height . 0.266305646565015) (rotation . 0.0)))
  ("TEXT" "CACEM - TESTI" ((content . "SEZIONE LONGITUDINALE ARMATURA") (position . ((x . -216.476934683763) (y . 136.89069993528))) (height . 0.266305646565015) (rotation . 0.0)))
  ("TEXT" "CACEM - TESTI" ((content . "228") (position . ((x . -222.419679678302) (y . 134.896495614607))) (height . 0.0974217639170123) (rotation . 0.0)))
  ("TEXT" "CACEM - TESTI" ((content . "DISTINTA  ACCIAIO") (position . ((x . -224.961889557327) (y . 136.851024060762))) (height . 0.267909850771784) (rotation . 0.0)))
  ("TEXT" "CACEM - TESTI" ((content . "11") (position . ((x . -225.984454877609) (y . 136.558328696425))) (height . 0.11690611408736) (rotation . 0.0)))
  ("TEXT" "CACEM - TESTI" ((content . "11") (position . ((x . -225.343543276448) (y . 136.558328696425))) (height . 0.11690611408736) (rotation . 0.0)))
  ("TEXT" "CACEM - TESTI" ((content . "11") (position . ((x . -224.767084427427) (y . 136.558328696425))) (height . 0.11690611408736) (rotation . 0.0)))
  ("TEXT" "CACEM - TESTI" ((content . "11") (position . ((x . -222.415715279267) (y . 136.558328696425))) (height . 0.11690611408736) (rotation . 0.0)))
  ("TEXT" "CACEM - TESTI" ((content . "11") (position . ((x . -223.70084657116) (y . 136.558328696425))) (height . 0.11690611408736) (rotation . 0.0)))
  ("TEXT" "CACEM - TESTI" ((content . "11") (position . ((x . -224.33041939675) (y . 136.558328696425))) (height . 0.11690611408736) (rotation . 0.0)))
  ("TEXT" "CACEM - TESTI" ((content . "11") (position . ((x . -225.930659130238) (y . 136.055717377224))) (height . 0.233812233400829) (rotation . 0.0)))
  ("TEXT" "CACEM - TESTI" ((content . "11") (position . ((x . -225.92841047548) (y . 135.537369652295))) (height . 0.233812233400829) (rotation . 0.0)))
  ("TEXT" "CACEM - TESTI" ((content . "11") (position . ((x . -225.930671056653) (y . 134.93536709218))) (height . 0.233812233400829) (rotation . 0.0)))
  ("TEXT" "CACEM - TESTI" ((content . "11") (position . ((x . -225.930671272923) (y . 134.375191949659))) (height . 0.233812233400829) (rotation . 0.0)))
  ("TEXT" "CACEM - TESTI" ((content . "11") (position . ((x . -225.473253396131) (y . 136.093439855526))) (height . 0.194843527834025) (rotation . 0.0)))
  ("TEXT" "CACEM - TESTI" ((content . "11") (position . ((x . 41) (y . 133.476444497302))) (height . 0.194843527834025) (rotation . 0.0)))
  ("TEXT" "CACEM - TESTI" ((content . "11") (position . ((x . -224.855914231456) (y . 136.106862872597))) (height . 0.194843527834025) (rotation . 0.0)))
  ("TEXT" "CACEM - TESTI" ((content . "11") (position . ((x . -224.249899360291) (y . 41))) (height . 0.194843527834025) (rotation . 0.0)))
  ("TEXT" "CACEM - TESTI" ((content . "11") (position . ((x . -225.473276080622) (y . 134.93232267415))) (height . 0.194843527834025) (rotation . 0.0)))
  ("TEXT" "CACEM - TESTI" ((content . "11") (position . ((x . -223.693364695859) (y . 134.946909650267))) (height . 0.170488086854772) (rotation . 0.0)))
  ("TEXT" "CACEM - TESTI" ((content . "11") (position . ((x . -224.855936915951) (y . 134.94574569122))) (height . 0.194843527834025) (rotation . 0.0)))
  ("TEXT" "CACEM - TESTI" ((content . "in testata") (position . ((x . -223.156396544176) (y . 134.904993354124))) (height . 0.0974217639170123) (rotation . 0.0)))
  ("TEXT" "CACEM - TESTI" ((content . "11") (position . ((x . -225.930671272923) (y . 133.519081502621))) (height . 0.233812233400829) (rotation . 0.0)))
  ("TEXT" "CACEM - TESTI" ((content . "PRESCRIZIONI MATERIALI") (position . ((x . -224.784057546946) (y . 125.164652242038))) (height . 0.181353976384767) (rotation . 0.0)))
  ("TEXT" "CACEM - TESTI" ((content . "Trefoli stabilizz.") (position . ((x . -226.012930443558) (y . 123.857094701932))) (height . 0.149697033467691) (rotation . 0.0)))
  ("TEXT" "CACEM - TESTI" ((content . "Tens. Tes. Tref...") (position . ((x . -226.012930443558) (y . 123.607390946366))) (height . 0.149697033467691) (rotation . 0.0)))
  ("TEXT" "CACEM - TESTI" ((content . "spi") (position . ((x . -223.916237699912) (y . 123.557725293777))) (height . 0.149697033467691) (rotation . 0.0)))
  ("TEXT" "CACEM - TESTI" ((content . "fptk") (position . ((x . -224.060410181102) (y . 123.831126302643))) (height . 0.149697033467691) (rotation . 0.0)))
  ("TEXT" "CACEM - TESTI" ((content . "Calcestruzzo .....") (position . ((x . -226.012930443558) (y . 124.819383493976))) (height . 0.149697033467691) (rotation . 0.0)))
  ("TEXT" "CACEM - TESTI" ((content . "Calcestruzzo .....") (position . ((x . -226.012930443558) (y . 124.59979148016))) (height . 0.149697033467691) (rotation . 0.0)))
  ("TEXT" "CACEM - TESTI" ((content . "Acciaio B450C") (position . ((x . -226.012930443558) (y . 124.377219150484))) (height . 0.149697033467691) (rotation . 0.0)))
  ("TEXT" "CACEM - TESTI" ((content . "Acciaio reti elettosald.") (position . ((x . -226.012930443558) (y . 124.120766644776))) (height . 0.149697033467691) (rotation . 0.0)))
  ("TEXT" "CACEM - TESTI" ((content . "Classe") (position . ((x . -224.026244932109) (y . 124.819383493976))) (height . 0.149697033467691) (rotation . 0.0)))
  ("TEXT" "CACEM - TESTI" ((content . "R") (position . ((x . -224.026244932109) (y . 124.59979148016))) (height . 0.149697033467691) (rotation . 0.0)))
  ("TEXT" "CACEM - TESTI" ((content . "f") (position . ((x . -224.001264059186) (y . 124.391179067034))) (height . 0.149697033467691) (rotation . 0.0)))
  ("TEXT" "CACEM - TESTI" ((content . "f") (position . ((x . -223.995752651612) (y . 124.140542208238))) (height . 0.149697033467691) (rotation . 0.0)))
  ("TEXT" "CACEM - TESTI" ((content . "yk") (position . ((x . -223.904934672018) (y . 124.339783777671))) (height . 0.149697033467691) (rotation . 0.0)))
  ("TEXT" "CACEM - TESTI" ((content . "yk") (position . ((x . -223.910424474535) (y . 124.083657118526))) (height . 0.149697033467691) (rotation . 0.0)))
  ("TEXT" "CACEM - TESTI" ((content . "ckj") (position . ((x . -223.915260015214) (y . 124.557802059879))) (height . 0.149697033467691) (rotation . 0.0)))
  ("TEXT" "CACEM - TESTI" ((content . "2") (position . ((x . -222.393531894087) (y . 123.919147735171))) (height . 0.149697033467691) (rotation . 0.0)))
  ("TEXT" "CACEM - TESTI" ((content . "11") (position . ((x . -223.310651335081) (y . 123.8572556857))) (height . 0.149697033467691) (rotation . 0.0)))
  ("TEXT" "CACEM - TESTI" ((content . "2") (position . ((x . -222.400865506699) (y . 123.688576120666))) (height . 0.149697033467691) (rotation . 0.0)))
  ("TEXT" "CACEM - TESTI" ((content . "11") (position . ((x . -223.32503108468) (y . 123.607390946366))) (height . 0.149697033467691) (rotation . 0.0)))
  ("TEXT" "CACEM - TESTI" ((content . ">") (position . ((x . -223.60506936942) (y . 123.585076517565))) (height . 0.149697033467691) (rotation . 0.0)))
  ("TEXT" "CACEM - TESTI" ((content . ">") (position . ((x . -223.622430557427) (y . 123.843097133798))) (height . 0.149697033467691) (rotation . 0.0)))
  ("TEXT" "CACEM - TESTI" ((content . "11") (position . ((x . -222.852811249467) (y . 123.611627960489))) (height . 0.149697033467691) (rotation . 0.0)))
  ("TEXT" "CACEM - TESTI" ((content . "2") (position . ((x . -222.400865506699) (y . 124.67674018284))) (height . 0.149697033467691) (rotation . 0.0)))
  ("TEXT" "CACEM - TESTI" ((content . "2") (position . ((x . -222.400865506699) (y . 124.193637752442))) (height . 0.149697033467691) (rotation . 0.0)))
  ("TEXT" "CACEM - TESTI" ((content . "2") (position . ((x . -222.400865506699) (y . 124.446168568336))) (height . 0.149697033467691) (rotation . 0.0)))
  ("TEXT" "CACEM - TESTI" ((content . "11") (position . ((x . -223.22576851217) (y . 124.59979148016))) (height . 0.149697033467691) (rotation . 0.0)))
  ("TEXT" "CACEM - TESTI" ((content . "11") (position . ((x . -223.230314841597) (y . 124.819383493976))) (height . 0.209575846854768) (rotation . 0.0)))
  ("TEXT" "CACEM - TESTI" ((content . "11") (position . ((x . -223.2701858256) (y . 124.369219865656))) (height . 0.149697033467691) (rotation . 0.0)))
  ("TEXT" "CACEM - TESTI" ((content . "11") (position . ((x . -223.272923077712) (y . 124.116689049762))) (height . 0.149697033467691) (rotation . 0.0)))
  ("TEXT" "CACEM - TESTI" ((content . ">") (position . ((x . -223.60506936942) (y . 124.611669182157))) (height . 0.149697033467691) (rotation . 0.0)))
  ("TEXT" "CACEM - TESTI" ((content . ">") (position . ((x . -223.60506936942) (y . 124.128566751759))) (height . 0.149697033467691) (rotation . 0.0)))
  ("TEXT" "CACEM - TESTI" ((content . ">") (position . ((x . -223.60506936942) (y . 124.359138366264))) (height . 0.149697033467691) (rotation . 0.0)))
  ("TEXT" "CACEM - TESTI" ((content . "11") (position . ((x . -222.852811249467) (y . 124.599792022663))) (height . 0.149697033467691) (rotation . 0.0)))
  ("TEXT" "CACEM - TESTI" ((content . "11") (position . ((x . -222.852811249467) (y . 124.369220408158))) (height . 0.149697033467691) (rotation . 0.0)))
  ("TEXT" "CACEM - TESTI" ((content . "11") (position . ((x . -222.852811249467) (y . 124.116689592266))) (height . 0.149697033467691) (rotation . 0.0)))
  ("TEXT" "CACEM - TESTI" ((content . "11") (position . ((x . -225.930671272923) (y . 132.635229054551))) (height . 0.233812233400829) (rotation . 0.0)))
  ("TEXT" "CACEM - TESTI" ((content . "%%Utrasporto") (position . ((x . -211.207974400401) (y . 124.019366721607))) (height . 0.229293240368254) (rotation . 0.0)))
  ("TEXT" "CACEM - TESTI" ((content . "%%Ustoccaggio") (position . ((x . -213.729218991574) (y . 124.019366721607))) (height . 0.229293240368254) (rotation . 0.0)))
  ("TEXT" "CACEM - TESTI" ((content . "%%usollevamento") (position . ((x . -216.214728677321) (y . 124.019366721607))) (height . 0.229293240368254) (rotation . 0.0)))
  ("TEXT" "CACEM - TESTI" ((content . "DISTINTA INSERTI") (position . ((x . -212.378935332751) (y . 123.175094120092))) (height . 0.181353976384767) (rotation . 0.0)))
  ("TEXT" "CACEM - TESTI" ((content . "11") (position . ((x . -212.158001481156) (y . 121.909128075642))) (height . 0.107332030058009) (rotation . 0.0)))
  ("TEXT" "CACEM - TESTI" ((content . "11") (position . ((x . -213.439091815991) (y . 121.909128288897))) (height . 0.132992916015496) (rotation . 0.0)))
  ("TEXT" "CACEM - TESTI" ((content . "11") (position . ((x . -213.237866625337) (y . 121.596076612857))) (height . 0.132992916015496) (rotation . 0.0)))
  ("TEXT" "CACEM - TESTI" ((content . "11") (position . ((x . -213.358415204211) (y . 122.535231427701))) (height . 0.132992916015496) (rotation . 0.0)))
  ("TEXT" "CACEM - TESTI" ((content . "11") (position . ((x . -213.121297580449) (y . 122.919552767374))) (height . 0.107332030058009) (rotation . 0.0)))
  ("TEXT" "CACEM - TESTI" ((content . "11") (position . ((x . -213.204989740189) (y . 122.222179751672))) (height . 0.132992916015496) (rotation . 0.0)))
  ("TEXT" "CACEM - TESTI" ((content . "11") (position . ((x . -212.158001481156) (y . 122.535231427701))) (height . 0.107332030058009) (rotation . 0.0)))
  ("TEXT" "CACEM - TESTI" ((content . "11") (position . ((x . -212.208607142259) (y . 122.919552767374))) (height . 0.107332030058009) (rotation . 0.0)))
  ("TEXT" "CACEM - TESTI" ((content . "11") (position . ((x . -212.226383552148) (y . 122.222179751672))) (height . 0.107332030058009) (rotation . 0.0)))
  ("TEXT" "CACEM - TESTI" ((content . "11") (position . ((x . -210.847497884034) (y . 121.909128075642))) (height . 0.107332030058009) (rotation . 0.0)))
  ("TEXT" "CACEM - TESTI" ((content . "11") (position . ((x . -211.536324093479) (y . 121.909128075642))) (height . 0.107332030058009) (rotation . 0.0)))
  ("TEXT" "CACEM - TESTI" ((content . "11") (position . ((x . -211.536324093479) (y . 122.535231427701))) (height . 0.107332030058009) (rotation . 0.0)))
  ("TEXT" "CACEM - TESTI" ((content . "( kN )") (position . ((x . -211.632706434941) (y . 122.805512395055))) (height . 0.0894433603808891) (rotation . 0.0)))
  ("TEXT" "CACEM - TESTI" ((content . "11") (position . ((x . -211.68526725362) (y . 122.919552767374))) (height . 0.107332030058009) (rotation . 0.0)))
  ("TEXT" "CACEM - TESTI" ((content . "11") (position . ((x . -211.536324093479) (y . 122.222179751672))) (height . 0.107332030058009) (rotation . 0.0)))
  ("TEXT" "CACEM - TESTI" ((content . "(cm)") (position . ((x . -210.899158374706) (y . 122.805512395055))) (height . 0.0894433603808891) (rotation . 0.0)))
  ("TEXT" "CACEM - TESTI" ((content . "11") (position . ((x . -210.923020982624) (y . 122.919552767374))) (height . 0.107332030058009) (rotation . 0.0)))
  ("TEXT" "CACEM - TESTI" ((content . "11") (position . ((x . -210.847497884034) (y . 122.222179751672))) (height . 0.107332030058009) (rotation . 0.0)))
  ("TEXT" "CACEM - TESTI" ((content . "11") (position . ((x . -210.440186113308) (y . 122.222179751672))) (height . 0.107332030058009) (rotation . 0.0)))
  ("TEXT" "CACEM - TESTI" ((content . "11") (position . ((x . -210.435700724554) (y . 122.919552767374))) (height . 0.107332030058009) (rotation . 0.0)))
  ("TEXT" "CACEM - TESTI" ((content . "11") (position . ((x . -210.372199603047) (y . 122.805512395055))) (height . 0.0894433603808891) (rotation . 0.0)))
  ("TEXT" "CACEM - TESTI" ((content . "%%C") (position . ((x . -215.423501341512) (y . 121.709764243629))) (height . 0.124226889417901) (rotation . 0.0)))
  ("TEXT" "CACEM - TESTI" ((content . "INTERASSE STAFFE  .............................................................    +2.5") (position . ((x . -226.061069456537) (y . 121.654232423184))) (height . 0.134165040571334) (rotation . 0.0)))
  ("TEXT" "CACEM - TESTI" ((content . "PRESCRIZIONI PIEGATURA FERRI") (position . ((x . -216.350903082015) (y . 123.159593668266))) (height . 0.181353976384767) (rotation . 0.0)))
  ("TEXT" "CACEM - TESTI" ((content . "11") (position . ((x . -216.054688882288) (y . 122.313899204906))) (height . 0.149072267301482) (rotation . 0.0)))
  ("TEXT" "CACEM - TESTI" ((content . "LARGHEZZA ED ALTEZZA ...................................................    +1.0") (position . ((x . -226.038002273198) (y . 122.54367352893))) (height . 0.134165040571334) (rotation . 0.0)))
  ("TEXT" "CACEM - TESTI" ((content . "POSIZIONE ARMATURA LENTA...........................................    +0.5") (position . ((x . -226.037760713985) (y . 121.868896488095))) (height . 0.134165040571334) (rotation . 0.0)))
  ("TEXT" "CACEM - TESTI" ((content . "POSIZIONE ARMATURA DI PRECOMPRESSIONE..............    +0.5") (position . ((x . -226.037760713985) (y . 122.083560553007))) (height . 0.134165040571334) (rotation . 0.0)))
  ("TEXT" "CACEM - TESTI" ((content . "SPESSORI ED ALTEZZA.........................................................    +0.5") (position . ((x . -226.057622608243) (y . 122.32093727116))) (height . 0.134165040571334) (rotation . 0.0)))
  ("TEXT" "CACEM - TESTI" ((content . "TOLLERANZE DI PRODUZIONE  ( cm. )") (position . ((x . -225.444622936883) (y . 123.128690862534))) (height . 0.181353976384767) (rotation . 0.0)))
  ("TEXT" "CACEM - TESTI" ((content . "LUNGHEZZA ELEMENTO     ...................................................    +1.0") (position . ((x . -226.046522063784) (y . 122.770359687968))) (height . 0.134165040571334) (rotation . 0.0)))
  ("TEXT" "CACEM - TESTI" ((content . "11") (position . ((x . -214.772998634248) (y . 122.797926481399))) (height . 0.149072267301482) (rotation . 0.0)))
  ("TEXT" "CACEM - TESTI" ((content . "11") (position . ((x . -214.846815817003) (y . 122.350709510549))) (height . 0.149072267301482) (rotation . 0.0)))
  ("TEXT" "CACEM - TESTI" ((content . "11") (position . ((x . -214.730344214669) (y . 121.779265655242))) (height . 0.149072267301482) (rotation . 0.0)))
  ("TEXT" "CACEM - TESTI" ((content . "11") (position . ((x . -213.825937260171) (y . 122.797926481399))) (height . 0.149072267301482) (rotation . 0.0)))
  ("TEXT" "CACEM - TESTI" ((content . "11") (position . ((x . -213.902615642181) (y . 121.779265655242))) (height . 0.149072267301482) (rotation . 0.0)))
  ("TEXT" "CACEM - TESTI" ((content . "11") (position . ((x . -213.909323894209) (y . 122.350709510549))) (height . 0.149072267301482) (rotation . 0.0)))
  ("TEXT" "CACEM - TESTI" ((content . "11") (position . ((x . -225.401833453749) (y . 134.38054146004))) (height . 0.194843527834025) (rotation . 0.0)))
  ("TEXT" "CACEM - TESTI" ((content . "11") (position . ((x . 41) (y . 134.39396447711))) (height . 0.194843527834025) (rotation . 0.0)))
  ("TEXT" "CACEM - TESTI" ((content . "11") (position . ((x . 41) (y . 132.597758333353))) (height . 0.194843527834025) (rotation . 0.0)))
  ("TEXT" "CACEM - TESTI" ((content . "11") (position . ((x . -224.249899360291) (y . 41))) (height . 0.194843527834025) (rotation . 0.0)))
  ("TEXT" "CACEM - TESTI" ((content . "11") (position . ((x . -225.932882870229) (y . 130.166114560173))) (height . 0.233812233400829) (rotation . 0.0)))
  ("TEXT" "CACEM - TESTI" ((content . "11") (position . ((x . 41) (y . 129.330525658799))) (height . 0.194843527834025) (rotation . 0.0)))
  ("TEXT" "CACEM - TESTI" ((content . "11") (position . ((x . -224.249899360291) (y . 41))) (height . 0.194843527834025) (rotation . 0.0)))
  ("TEXT" "CACEM - TESTI" ((content . "11") (position . ((x . 41) (y . 128.277996723399))) (height . 0.194843527834025) (rotation . 0.0)))
  ("TEXT" "CACEM - TESTI" ((content . "11") (position . ((x . -224.249899360291) (y . 41))) (height . 0.194843527834025) (rotation . 0.0)))
  ("TEXT" "CACEM - TESTI" ((content . "11") (position . ((x . -225.429073181664) (y . 130.179684885831))) (height . 0.194843527834025) (rotation . 0.0)))
  ("TEXT" "CACEM - TESTI" ((content . "11") (position . ((x . -224.877805286814) (y . 130.195277873682))) (height . 0.194843527834025) (rotation . 0.0)))
  ("TEXT" "CACEM - TESTI" ((content . "64") (position . ((x . -222.471269214998) (y . 132.844332641499))) (height . 0.0974217639170123) (rotation . 0.0)))
  ("TEXT" "CACEM - TESTI" ((content . "10") (position . ((x . 41) (y . 132.691333347239))) (height . 0.0974217639170123) (rotation . 0.0)))
  ("TEXT" "CACEM - TESTI" ((content . "11") (position . ((x . -223.717739054182) (y . 133.467136340803))) (height . 0.194843527834025) (rotation . 0.0)))
  ("TEXT" "CACEM - TESTI" ((content . "11") (position . ((x . -222.011690289304) (y . 134.084073700615))) (height . 0.0974217639170123) (rotation . 0.0)))
  ("TEXT" "CACEM - TESTI" ((content . "11") (position . ((x . -222.177333168277) (y . 133.269660798448))) (height . 0.0974217639170123) (rotation . 0.0)))
  ("TEXT" "CACEM - TESTI" ((content . "11") (position . ((x . -222.135796720224) (y . 133.777132424082))) (height . 0.0974217639170123) (rotation . 0.0)))
  ("TEXT" "CACEM - TESTI" ((content . "11") (position . ((x . -222.573831182742) (y . 133.588621159066))) (height . 0.0974217639170123) (rotation . 0.0)))
  ("TEXT" "CACEM - TESTI" ((content . "11") (position . ((x . -223.656038603701) (y . 132.588450176854))) (height . 0.194843527834025) (rotation . 0.0)))
  ("TEXT" "CACEM - TESTI" ((content . "37") (position . ((x . -222.542306556544) (y . 130.204772844135))) (height . 0.0974217639170123) (rotation . 0.0)))
  ("TEXT" "CACEM - TESTI" ((content . "150") (position . ((x . -222.09699579806) (y . 130.421297493241))) (height . 0.0974217639170123) (rotation . 0.0)))
  ("TEXT" "CACEM - TESTI" ((content . "11") (position . ((x . -223.739588507701) (y . 130.167941054515))) (height . 0.194843527834025) (rotation . 0.0)))
  ("TEXT" "CACEM - TESTI" ((content . "11") (position . ((x . -223.717739054182) (y . 129.321217502299))) (height . 0.194843527834025) (rotation . 0.0)))
  ("TEXT" "CACEM - TESTI" ((content . "64") (position . ((x . -222.471269214998) (y . 128.48339922192))) (height . 0.0974217639170123) (rotation . 0.0)))
  ("TEXT" "CACEM - TESTI" ((content . "10") (position . ((x . 41) (y . 128.330399927659))) (height . 0.0974217639170123) (rotation . 0.0)))
  ("TEXT" "CACEM - TESTI" ((content . "11") (position . ((x . -223.656038603701) (y . 128.2686885669))) (height . 0.194843527834025) (rotation . 0.0)))
  ("TEXT" "CACEM - TESTI" ((content . "in testata") (position . ((x . -223.156396544176) (y . 130.174437503484))) (height . 0.0974217639170123) (rotation . 0.0)))
  ("TEXT" "CACEM - TESTI" ((content . "150") (position . ((x . -222.09699579806) (y . 130.176870694129))) (height . 0.0974217639170123) (rotation . 0.0)))
  ("TEXT" "CACEM - TESTI" ((content . "INTEGRAZIONE APPOGGIO TEGOLO") (position . ((x . -223.156396544176) (y . 128.745026582937))) (height . 0.08) (rotation . 0.0)))
  ("TEXT" "CACEM - TESTI" ((content . "INTEGRAZIONE APPOGGIO TEGOLO") (position . ((x . -223.156396544176) (y . 128.114833482629))) (height . 0.08) (rotation . 0.0)))
  ("TEXT" "CACEM - TESTI" ((content . "3") (position . ((x . -208.234257148737) (y . 135.186030002467))) (height . 0.139566613331816) (rotation . 0.0)))
  ("TEXT" "CACEM - TESTI" ((content . "A") (position . ((x . -208.200316711364) (y . 135.795473970067))) (height . 0.228050021784013) (rotation . 0.0)))
  ("TEXT" "CACEM - TESTI" ((content . "A") (position . ((x . -215.56077670657) (y . 135.762139745506))) (height . 0.228050021784013) (rotation . 0.0)))
  ("TEXT" "CACEM - TESTI" ((content . "2") (position . ((x . -210.797963823564) (y . 134.463199790926))) (height . 0.139566613331816) (rotation . 0.0)))
  ("TEXT" "CACEM - TESTI" ((content . "4") (position . ((x . -211.302285699434) (y . 134.516433181473))) (height . 0.139566613331816) (rotation . 0.0)))
  ("TEXT" "CACEM - TESTI" ((content . "41") (position . ((x . -210.585709556789) (y . 135.917646773024))) (height . 0.139566613331816) (rotation . 0.0)))
  ("TEXT" "CACEM - TESTI" ((content . "7") (position . ((x . -214.593191955747) (y . 134.463199790926))) (height . 0.139566613331816) (rotation . 0.0)))
  ("TEXT" "CACEM - TESTI" ((content . "11") (position . ((x . -224.855955833294) (y . 127.511964188628))) (height . 0.194843527834025) (rotation . 0.0)))
  ("TEXT" "CACEM - TESTI" ((content . "11") (position . ((x . 41) (y . 127.504832966007))) (height . 0.243264711370076) (rotation . 0.0)))
  ("TEXT" "CACEM - TESTI" ((content . "11") (position . ((x . -223.727481230574) (y . 127.502656032129))) (height . 0.194843527834025) (rotation . 0.0)))
  ("TEXT" "CACEM - TESTI" ((content . "50") (position . ((x . -222.431781821375) (y . 127.629901091118))) (height . 0.0974217639170123) (rotation . 41)))
  ("TEXT" "CACEM - TESTI" ((content . "15") (position . ((x . -221.991736956809) (y . 127.426686312202))) (height . 0.0974217639170123) (rotation . 0.0)))
  ("TEXT" "CACEM - TESTI" ((content . "32") (position . ((x . -222.189844806636) (y . 127.290041878552))) (height . 0.0974217639170123) (rotation . 0.0)))
  ("TEXT" "CACEM - TESTI" ((content . "40") (position . ((x . -222.232842212387) (y . 127.565125252383))) (height . 41) (rotation . 0.0)))
  ("TEXT" "CACEM - TESTI" ((content . "10") (position . ((x . 41) (y . 127.441289531165))) (height . 0.0974217639170123) (rotation . 0.0)))
  ("TEXT" "CACEM - TESTI" ((content . "11") (position . ((x . -224.630629559198) (y . 126.319260042803))) (height . 0.18) (rotation . 90)))
  ("TEXT" "CACEM - TESTI" ((content . "11") (position . ((x . -226.000341487832) (y . 126.656913575827))) (height . 0.233812233400829) (rotation . 0.0)))
  ("TEXT" "CACEM - TESTI" ((content . "11") (position . ((x . -225.282963220279) (y . 126.643621892363))) (height . 0.194843527834025) (rotation . 0.0)))
  ("TEXT" "CACEM - TESTI" ((content . "11") (position . ((x . -223.724233838443) (y . 126.618108675723))) (height . 0.194843527834025) (rotation . 0.0)))
  ("TEXT" "CACEM - TESTI" ((content . "15") (position . ((x . -221.348810336013) (y . 126.668543703395))) (height . 0.0974217639170123) (rotation . 0.0)))
  ("TEXT" "CACEM - TESTI" ((content . "94") (position . ((x . -222.173693769959) (y . 126.471094452299))) (height . 0.0974217639170123) (rotation . 0.0)))
  ("TEXT" "CACEM - TESTI" ((content . "10") (position . ((x . 41) (y . 126.66445316903))) (height . 0.0974217639170123) (rotation . 0.0)))
  ("TEXT" "CACEM - TESTI" ((content . "40") (position . ((x . -221.762018115823) (y . 126.867787461021))) (height . 41) (rotation . 0.0)))
  ("TEXT" "CACEM - TESTI" ((content . "11") (position . ((x . -224.340825356453) (y . 126.696351795222))) (height . 0.194843527834025) (rotation . 0.0)))
  ("TEXT" "CACEM - TESTI" ((content . "11") (position . ((x . -226.06504219125) (y . 126.334280568135))) (height . 0.233812233400829) (rotation . 0.0)))
  ("TEXT" "CACEM - TESTI" ((content . "11") (position . ((x . -224.421546246556) (y . 126.444540632658))) (height . 0.194843527834025) (rotation . 0.0)))
  ("TEXT" "CACEM - TESTI" ((content . "11") (position . ((x . -224.196084450062) (y . 126.951301788135))) (height . 0.194843527834025) (rotation . 0.0)))
  ("TEXT" "CACEM - TESTI" ((content . "11") (position . ((x . -225.992775749594) (y . 130.819705631668))) (height . 0.233812233400829) (rotation . 0.0)))
  ("TEXT" "CACEM - TESTI" ((content . "11") (position . ((x . 41) (y . 130.782234910469))) (height . 0.194843527834025) (rotation . 0.0)))
  ("TEXT" "CACEM - TESTI" ((content . "11") (position . ((x . -224.249899360291) (y . 41))) (height . 0.194843527834025) (rotation . 0.0)))
  ("TEXT" "CACEM - TESTI" ((content . "64") (position . ((x . -222.471269214998) (y . 130.98763740899))) (height . 0.0974217639170123) (rotation . 0.0)))
  ("TEXT" "CACEM - TESTI" ((content . "10") (position . ((x . 41) (y . 130.83463811473))) (height . 0.0974217639170123) (rotation . 0.0)))
  ("TEXT" "CACEM - TESTI" ((content . "11") (position . ((x . -223.656038603701) (y . 130.77292675397))) (height . 0.194843527834025) (rotation . 0.0)))
  ("TEXT" "CACEM - TESTI" ((content . "11") (position . ((x . 41) (y . 131.627506919852))) (height . 0.194843527834025) (rotation . 0.0)))
  ("TEXT" "CACEM - TESTI" ((content . "11") (position . ((x . -224.249899360291) (y . 41))) (height . 0.194843527834025) (rotation . 0.0)))
  ("TEXT" "CACEM - TESTI" ((content . "11") (position . ((x . -225.992775749594) (y . 131.670143925171))) (height . 0.233812233400829) (rotation . 0.0)))
  ("TEXT" "CACEM - TESTI" ((content . "11") (position . ((x . -223.717739054182) (y . 131.618198763353))) (height . 0.194843527834025) (rotation . 0.0)))
  ("TEXT" "CACEM - TESTI" ((content . "11") (position . ((x . -222.011690289304) (y . 132.187375163256))) (height . 0.0974217639170123) (rotation . 0.0)))
  ("TEXT" "CACEM - TESTI" ((content . "11") (position . ((x . -222.177333168277) (y . 131.345102534079))) (height . 0.0974217639170123) (rotation . 0.0)))
  ("TEXT" "CACEM - TESTI" ((content . "11") (position . ((x . -222.135796720224) (y . 131.852574159712))) (height . 0.0974217639170123) (rotation . 0.0)))
  ("TEXT" "CACEM - TESTI" ((content . "11") (position . ((x . -222.573831182742) (y . 131.664062894696))) (height . 0.0974217639170123) (rotation . 0.0)))
  ("MTEXT" "CACEM - TESTI" ((content . "44") (position . ((x . -211.10142921839) (y . 131.149346584936))) (height . 0.12) (rotation . 0.0)))
  ("MTEXT" "CACEM - TESTI" ((content . "44") (position . ((x . -211.49985584929) (y . 129.243081997123))) (height . 0.12) (rotation . 0.0)))
  ("TEXT" "CACEM - TESTI" ((content . "11") (position . ((x . -224.855955833294) (y . 125.833359093751))) (height . 0.194843527834025) (rotation . 0.0)))
  ("TEXT" "CACEM - TESTI" ((content . "11") (position . ((x . 41) (y . 125.812393275646))) (height . 0.243264711370076) (rotation . 0.0)))
  ("TEXT" "CACEM - TESTI" ((content . "11") (position . ((x . -226.000341487832) (y . 125.862855837357))) (height . 0.233812233400829) (rotation . 0.0)))
  ("TEXT" "CACEM - TESTI" ((content . "11") (position . ((x . -223.727481230574) (y . 125.824050937252))) (height . 0.194843527834025) (rotation . 0.0)))
  ("TEXT" "CACEM - TESTI" ((content . "50") (position . ((x . -222.431781821375) (y . 125.951295996241))) (height . 0.0974217639170123) (rotation . 41)))
  ("TEXT" "CACEM - TESTI" ((content . "15") (position . ((x . -221.991736956809) (y . 125.748081217325))) (height . 0.0974217639170123) (rotation . 0.0)))
  ("TEXT" "CACEM - TESTI" ((content . "32") (position . ((x . -222.189844806636) (y . 125.611436783675))) (height . 0.0974217639170123) (rotation . 0.0)))
  ("TEXT" "CACEM - TESTI" ((content . "40") (position . ((x . -222.232842212387) (y . 125.886520157505))) (height . 41) (rotation . 0.0)))
  ("TEXT" "CACEM - TESTI" ((content . "10") (position . ((x . 41) (y . 125.762684436288))) (height . 0.0974217639170123) (rotation . 0.0)))
  ("TEXT" "CACEM - TESTI" ((content . "SEZ. IN TESTATA") (position . ((x . -220.14148979397) (y . 136.886823453544))) (height . 0.252517212072896) (rotation . 0.0)))
  ("TEXT" "CACEM - TESTI" ((content . "SEZ. IN MEZZERIA") (position . ((x . -220.308421510934) (y . 131.755212121471))) (height . 0.252517212072896) (rotation . 0.0)))
  ("TEXT" "CACEM - TESTI" ((content . "41") (position . ((x . -220.908386225164) (y . 136.18174780043))) (height . 0.158635849251743) (rotation . 0.0)))
  ("TEXT" "CACEM - TESTI" ((content . "4") (position . ((x . -220.959168669918) (y . 135.32989902023))) (height . 0.158635849251743) (rotation . 0.0)))
  ("TEXT" "CACEM - TESTI" ((content . "4") (position . ((x . -220.959168669918) (y . 134.711899020231))) (height . 0.158635849251743) (rotation . 0.0)))
  ("TEXT" "CACEM - TESTI" ((content . "4") (position . ((x . -220.959168669918) (y . 134.031840145727))) (height . 0.158635849251743) (rotation . 0.0)))
  ("TEXT" "CACEM - TESTI" ((content . "3") (position . ((x . -220.878190357421) (y . 133.329329100593))) (height . 0.158635849251743) (rotation . 0.0)))
  ("TEXT" "CACEM - TESTI" ((content . "2") (position . ((x . -218.282181673762) (y . 133.426443238299))) (height . 0.158635849251743) (rotation . 0.0)))
  ("TEXT" "CACEM - TESTI" ((content . "7") (position . ((x . -219.295864985789) (y . 133.309418333194))) (height . 0.158635849251743) (rotation . 0.0)))
  ("TEXT" "CACEM - TESTI" ((content . "5") (position . ((x . -217.975880149237) (y . 135.101223117143))) (height . 0.158635849251743) (rotation . 0.0)))
  ("TEXT" "CACEM - TESTI" ((content . "6") (position . ((x . -219.829438796212) (y . 134.482730923945))) (height . 0.158635849251743) (rotation . 0.0)))
  ("TEXT" "CACEM - TESTI" ((content . "41") (position . ((x . -220.908386225164) (y . 131.043083327069))) (height . 0.158635849251743) (rotation . 0.0)))
  ("TEXT" "CACEM - TESTI" ((content . "4") (position . ((x . -220.94287253884) (y . 130.19123454687))) (height . 0.158635849251743) (rotation . 0.0)))
  ("TEXT" "CACEM - TESTI" ((content . "4") (position . ((x . -220.94287253884) (y . 129.573234546869))) (height . 0.158635849251743) (rotation . 0.0)))
  ("TEXT" "CACEM - TESTI" ((content . "4") (position . ((x . -220.94287253884) (y . 128.893175672367))) (height . 0.158635849251743) (rotation . 0.0)))
  ("TEXT" "CACEM - TESTI" ((content . "5") (position . ((x . -217.975880149237) (y . 129.962558643782))) (height . 0.158635849251743) (rotation . 0.0)))
  ("TEXT" "CACEM - TESTI" ((content . "2") (position . ((x . -219.185484519746) (y . 128.287778764938))) (height . 0.158635849251743) (rotation . 0.0)))
  ("TEXT" "CACEM - TESTI" ((content . "4") (position . ((x . -217.907723957499) (y . 133.196800574982))) (height . 0.158635849251743) (rotation . 0.0)))
  ("TEXT" "CACEM - TESTI" ((content . "4") (position . ((x . -217.907723957499) (y . 128.058136101621))) (height . 0.158635849251743) (rotation . 0.0)))
  ("TEXT" "CACEM - TESTI" ((content . "11") (position . ((x . -219.660467125267) (y . 128.220630329513))) (height . 0.158635849251743) (rotation . 0.0)))
  ("TEXT" "CACEM - TESTI" ((content . "11") (position . ((x . -219.931371872049) (y . 133.359294802873))) (height . 0.158635849251743) (rotation . 0.0)))
  ("TEXT" "CACEM - TESTI" ((content . "6") (position . ((x . -219.773551450341) (y . 129.344066450584))) (height . 0.158635849251743) (rotation . 0.0)))
  ("TEXT" "CACEM - TESTI" ((content . "10") (position . ((x . 41) (y . 129.479066450585))) (height . 0.158635849251743) (rotation . 0.0)))
  ("MTEXT" "CACEM - TESTI" ((content . "44") (position . ((x . -214.367222161487) (y . 133.761454390896))) (height . 0.15) (rotation . 0.0)))
  ("TEXT" "CACEM - TESTI" ((content . "TIPO") (position . ((x . -206.447175737106) (y . 121.564132875775))) (height . 0.251184700868646) (rotation . 0.0)))
  ("TEXT" "CACEM - TESTI" ((content . "REDAZIONE") (position . ((x . -209.762690819017) (y . 122.928424610568))) (height . 0.0765912389888675) (rotation . 0.0)))
  ("TEXT" "CACEM - TESTI" ((content . "APPROVAZIONE") (position . ((x . -209.762690819017) (y . 122.565095268215))) (height . 0.0765912389888675) (rotation . 0.0)))
  ("TEXT" "CACEM - TESTI" ((content . "VERIFICA") (position . ((x . -209.754375691954) (y . 122.743282369462))) (height . 0.0765912389888675) (rotation . 0.0)))
  ("TEXT" "CACEM - TESTI" ((content . "PROGETTAZIONE") (position . ((x . -209.845177180027) (y . 124.346808687752))) (height . 0.083728233622882) (rotation . 0.0)))
  ("TEXT" "CACEM - TESTI" ((content . "FIRMA") (position . ((x . -207.775077953104) (y . 123.097044094747))) (height . 0.0870354988509858) (rotation . 0.0)))
  ("TEXT" "CACEM - TESTI" ((content . "NOME") (position . ((x . -208.733193622905) (y . 123.100983273799))) (height . 0.0870354988509858) (rotation . 0.0)))
  ("TEXT" "CACEM - TESTI" ((content . "DATA") (position . ((x . -207.029328796665) (y . 123.100983273799))) (height . 0.0870354988509858) (rotation . 0.0)))
  ("TEXT" "CACEM - TESTI" ((content . "CARP. ARM. TRAVE") (position . ((x . -206.447175737106) (y . 122.008859508447))) (height . 0.251184700868646) (rotation . 0.0)))
  ("TEXT" "CACEM - TESTI" ((content . "TITOLO") (position . ((x . -206.43412848617) (y . 122.343879730335))) (height . 0.0870354988509858) (rotation . 0.0)))
  ("TEXT" "CACEM - TESTI" ((content . "codice") (position . ((x . -209.586576184128) (y . 125.093880978451))) (height . 0.113033115390891) (rotation . 0.0)))
  ("TEXT" "CACEM - TESTI" ((content . "KN") (position . ((x . -207.838420371527) (y . 124.933157213165))) (height . 0.110521268382204) (rotation . 0.0)))
  ("TEXT" "CACEM - TESTI" ((content . "peso") (position . ((x . -207.867013317529) (y . 125.097122742764))) (height . 0.125592350434323) (rotation . 0.0)))
  ("TEXT" "CACEM - TESTI" ((content . "n.") (position . ((x . -208.430539162041) (y . 125.103986679811))) (height . 0.113033115390891) (rotation . 0.0)))
  ("TEXT" "CACEM - TESTI" ((content . "41") (position . ((x . -208.469971403434) (y . 124.604408782802))) (height . 0.203459607703603) (rotation . 0.0)))
  ("TEXT" "CACEM - TESTI" ((content . "(") (position . ((x . -207.905723745785) (y . 124.929618646465))) (height . 0.110521268382204) (rotation . 0.0)))
  ("TEXT" "CACEM - TESTI" ((content . "volume") (position . ((x . -207.222852259251) (y . 125.118413775363))) (height . 0.125592350434323) (rotation . 0.0)))
  ("TEXT" "CACEM - TESTI" ((content . ")") (position . ((x . -207.64262262046) (y . 124.93246614611))) (height . 0.110521268382204) (rotation . 0.0)))
  ("TEXT" "CACEM - TESTI" ((content . "(") (position . ((x . -207.099106728693) (y . 124.909347305388))) (height . 0.110521268382204) (rotation . 0.0)))
  ("TEXT" "CACEM - TESTI" ((content . "mc.") (position . ((x . -207.046951082378) (y . 124.918319420679))) (height . 0.110521268382204) (rotation . 0.0)))
  ("TEXT" "CACEM - TESTI" ((content . ")") (position . ((x . -206.87581536791) (y . 124.905264372063))) (height . 0.110521268382204) (rotation . 0.0)))
  ("TEXT" "CACEM - TESTI" ((content . "Kg") (position . ((x . -205.626728108537) (y . 124.933157213165))) (height . 0.110521268382204) (rotation . 0.0)))
  ("TEXT" "CACEM - TESTI" ((content . "trecce") (position . ((x . -205.727438675194) (y . 125.128534979662))) (height . 0.125592350434323) (rotation . 0.0)))
  ("TEXT" "CACEM - TESTI" ((content . "Kg") (position . ((x . -206.253745100471) (y . 124.933157213165))) (height . 0.110521268382204) (rotation . 0.0)))
  ("TEXT" "CACEM - TESTI" ((content . "trefoli") (position . ((x . -206.414271305527) (y . 125.123474377512))) (height . 0.125592350434323) (rotation . 0.0)))
  ("TEXT" "CACEM - TESTI" ((content . "(") (position . ((x . -206.32104847473) (y . 124.929618646465))) (height . 0.110521268382204) (rotation . 0.0)))
  ("TEXT" "CACEM - TESTI" ((content . "(") (position . ((x . -205.694031482797) (y . 124.929618646465))) (height . 0.110521268382204) (rotation . 0.0)))
  ("TEXT" "CACEM - TESTI" ((content . ")") (position . ((x . -206.057947349406) (y . 124.93246614611))) (height . 0.110521268382204) (rotation . 0.0)))
  ("TEXT" "CACEM - TESTI" ((content . ")") (position . ((x . -205.430930357472) (y . 124.93246614611))) (height . 0.110521268382204) (rotation . 0.0)))
  ("TEXT" "CACEM - TESTI" ((content . "Kg") (position . ((x . -204.974499730471) (y . 124.933157213165))) (height . 0.110521268382204) (rotation . 0.0)))
  ("TEXT" "CACEM - TESTI" ((content . "(") (position . ((x . -205.04180310473) (y . 124.929618646465))) (height . 0.110521268382204) (rotation . 0.0)))
  ("TEXT" "CACEM - TESTI" ((content . ")") (position . ((x . -204.778701979406) (y . 124.93246614611))) (height . 0.110521268382204) (rotation . 0.0)))
  ("TEXT" "CACEM - TESTI" ((content . "ferri") (position . ((x . -205.039633724776) (y . 125.128534979662))) (height . 0.125592350434323) (rotation . 0.0)))
  ("TEXT" "CACEM - TESTI" ((content . "Contrada San Justa") (position . ((x . -206.460831440918) (y . 123.747028920524))) (height . 0.0413273189337857) (rotation . 0.0)))
  ("TEXT" "CACEM - TESTI" ((content . "UFFICI TECNICI E AMMINISTRATIVI") (position . ((x . -206.465583065239) (y . 123.815712728118))) (height . 0.0464932338005089) (rotation . 0.0)))
  ("TEXT" "CACEM - TESTI" ((content . "Tel. 0823 - 88 33 55") (position . ((x . -206.460831440918) (y . 123.607981114723))) (height . 0.0413273189337857) (rotation . 0.0)))
  ("TEXT" "CACEM - TESTI" ((content . "81050 - Pastorano (CE)") (position . ((x . -206.460831440918) (y . 123.676154275221))) (height . 0.0413273189337857) (rotation . 0.0)))
  ("TEXT" "CACEM - TESTI" ((content . "Fax 0823 - 88 33 34") (position . ((x . -206.455916409779) (y . 123.535732703542))) (height . 0.0413273189337857) (rotation . 0.0)))
  ("TEXT" "CACEM - TESTI" ((content . "Strada Statale Appia Km 196,600 Loc. Marotta") (position . ((x . -205.464497853715) (y . 123.747765513174))) (height . 0.0413273189337857) (rotation . 0.0)))
  ("TEXT" "CACEM - TESTI" ((content . "STABILIMENTO") (position . ((x . -205.469249478038) (y . 123.816449320768))) (height . 0.0464932338005089) (rotation . 0.0)))
  ("TEXT" "CACEM - TESTI" ((content . "81041 - Vitulazio (CE)") (position . ((x . -205.464497853715) (y . 123.676890867871))) (height . 0.0413273189337857) (rotation . 0.0)))
  ("TEXT" "CACEM - TESTI" ((content . "CACEM") (position . ((x . -205.479629317832) (y . 124.207191863154))) (height . 0.221879561861956) (rotation . 0.0)))
  ("TEXT" "CACEM - TESTI" ((content . "PREFABBRICATI") (position . ((x . -205.480935343591) (y . 124.058403429567))) (height . 0.115562271803102) (rotation . 0.0)))
  ("TEXT" "CACEM - TESTI" ((content . "CACEM  s.r.l.  divisione  PREFABBRICATI") (position . ((x . -206.462739949667) (y . 123.896526722305))) (height . 0.0602690067784375) (rotation . 0.0)))
  ("TEXT" "CACEM - TESTI" ((content . "Contrada San Justa") (position . ((x . -206.460831440918) (y . 123.747028920524))) (height . 0.0413273189337857) (rotation . 0.0)))
  ("TEXT" "CACEM - TESTI" ((content . "UFFICI TECNICI E AMMINISTRATIVI") (position . ((x . -206.465583065239) (y . 123.815712728118))) (height . 0.0464932338005089) (rotation . 0.0)))
  ("TEXT" "CACEM - TESTI" ((content . "Tel. 0823 - 88 33 55") (position . ((x . -206.460831440918) (y . 123.607981114723))) (height . 0.0413273189337857) (rotation . 0.0)))
  ("TEXT" "CACEM - TESTI" ((content . "81050 - Pastorano (CE)") (position . ((x . -206.460831440918) (y . 123.676154275221))) (height . 0.0413273189337857) (rotation . 0.0)))
  ("TEXT" "CACEM - TESTI" ((content . "e-mail: info@caturano.it") (position . ((x . -205.465199881032) (y . 123.54276976353))) (height . 0.0413273189337857) (rotation . 0.0)))
  ("TEXT" "CACEM - TESTI" ((content . "www.caturano.it") (position . ((x . -205.465199881032) (y . 123.60562067081))) (height . 0.0413273189337857) (rotation . 0.0)))
  ("TEXT" "CACEM - TESTI" ((content . "Fax 0823 - 88 33 34") (position . ((x . -206.455916409779) (y . 123.535732703542))) (height . 0.0413273189337857) (rotation . 0.0)))
  ("TEXT" "CACEM - TESTI" ((content . "Strada Statale Appia Km 196,600 Loc. Marotta") (position . ((x . -205.464497853715) (y . 123.747765513174))) (height . 0.0413273189337857) (rotation . 0.0)))
  ("TEXT" "CACEM - TESTI" ((content . "STABILIMENTO") (position . ((x . -205.469249478038) (y . 123.816449320768))) (height . 0.0464932338005089) (rotation . 0.0)))
  ("TEXT" "CACEM - TESTI" ((content . "81041 - Vitulazio (CE)") (position . ((x . -205.464497853715) (y . 123.676890867871))) (height . 0.0413273189337857) (rotation . 0.0)))
  ("TEXT" "CACEM - TESTI" ((content . "CACEM") (position . ((x . -205.479629317832) (y . 124.207191863154))) (height . 0.221879561861956) (rotation . 0.0)))
  ("TEXT" "CACEM - TESTI" ((content . "PREFABBRICATI") (position . ((x . -205.480935343591) (y . 124.058403429567))) (height . 0.115562271803102) (rotation . 0.0)))
  ("TEXT" "CACEM - TESTI" ((content . "ARM. DI PRECOMPRESSIONE") (position . ((x . -220.779733146222) (y . 126.753309832287))) (height . 0.3) (rotation . 0.0)))
  ("MTEXT" "CACEM - TESTI" ((content . "44") (position . ((x . -220.230980077995) (y . 126.531687174547))) (height . 0.261600157952529) (rotation . 0.0)))
  ("TEXT" "41" ((content . "8") (position . ((x . -219.875516766812) (y . 126.248992368081))) (height . 0.383680231663709) (rotation . 0.0)))
  ("MTEXT" "CACEM - TESTI" ((content . "44") (position . ((x . -209.263862070733) (y . 133.761454390895))) (height . 0.15) (rotation . 0.0)))
  ("TEXT" "CACEM - TESTI" ((content . "ARM. TRAVE") (position . ((x . -225.91456725817) (y . 137.930683229007))) (height . 1.8) (rotation . 0.0)))
  ("TEXT" "CACEM - TESTI" ((content . "-") (position . ((x . -208.847222969388) (y . 122.925567982202))) (height . 0.0768283635677804) (rotation . 0.0)))
  ("TEXT" "CACEM - TESTI" ((content . "11") (position . ((x . -222.011690289304) (y . 129.837899106671))) (height . 0.0974217639170123) (rotation . 0.0)))
  ("TEXT" "CACEM - TESTI" ((content . "11") (position . ((x . -222.177333168277) (y . 128.995626477493))) (height . 0.0974217639170123) (rotation . 0.0)))
  ("TEXT" "CACEM - TESTI" ((content . "11") (position . ((x . -222.135796720224) (y . 129.503098103127))) (height . 0.0974217639170123) (rotation . 0.0)))
  ("TEXT" "CACEM - TESTI" ((content . "11") (position . ((x . -222.573831182742) (y . 129.314586838111))) (height . 0.0974217639170123) (rotation . 0.0)))
  ("TEXT" "CACEM - TESTI" ((content . "11") (position . ((x . -212.158001481156) (y . 121.596076399613))) (height . 0.107332030058009) (rotation . 0.0)))
  ("TEXT" "CACEM - TESTI" ((content . "11") (position . ((x . -211.536324093479) (y . 121.596076399613))) (height . 0.107332030058009) (rotation . 0.0)))
  ("TEXT" "CACEM - TESTI" ((content . "11") (position . ((x . -210.847497884034) (y . 121.596076399613))) (height . 0.107332030058009) (rotation . 0.0)))
  ("TEXT" "CACEM - TESTI" ((content . "11") (position . ((x . -210.310069821481) (y . 121.596076399613))) (height . 0.107332030058009) (rotation . 0.0)))
  ("TEXT" "CACEM - TESTI" ((content . "11") (position . ((x . -210.847497884034) (y . 122.535231427712))) (height . 0.107332030058009) (rotation . 0.0)))
  ("TEXT" "CACEM - TESTI" ((content . "11") (position . ((x . -210.310069821481) (y . 122.535231427712))) (height . 0.107332030058009) (rotation . 0.0)))
  ("TEXT" "CACEM - TESTI" ((content . "11") (position . ((x . -210.310069821481) (y . 121.909128075642))) (height . 0.107332030058009) (rotation . 0.0)))
  ("MTEXT" "CACEM - TESTI" ((content . "44") (position . ((x . -220.604849044175) (y . 123.025644565117))) (height . 0.140146525954482) (rotation . 0.0)))
  ("MTEXT" "CACEM - TESTI" ((content . "44") (position . ((x . -219.894972244732) (y . 122.327797815135))) (height . 0.140146525954482) (rotation . 0.0)))
  ("MTEXT" "CACEM - TESTI" ((content . "44") (position . ((x . -220.886813283695) (y . 123.945356141693))) (height . 0.140146525954482) (rotation . 0.0)))
  ("MTEXT" "CACEM - TESTI" ((content . "44") (position . ((x . -218.697887335537) (y . 122.019255450286))) (height . 0.140146525954482) (rotation . 0.0)))
  ("MTEXT" "CACEM - TESTI" ((content . "44") (position . ((x . -219.135845229145) (y . 122.327797815135))) (height . 0.140146525954482) (rotation . 0.0)))
  ("MTEXT" "CACEM - TESTI" ((content . "44") (position . ((x . -219.924224293873) (y . 125.573179889231))) (height . 0.140146525954482) (rotation . 0.0)))
  ("MTEXT" "CACEM - TESTI" ((content . "44") (position . ((x . -220.604849044175) (y . 124.193532281404))) (height . 0.140146525954482) (rotation . 0.0)))
  ("MTEXT" "CACEM - TESTI" ((content . "44") (position . ((x . -218.347466164418) (y . 125.573179889231))) (height . 0.140146525954482) (rotation . 0.0)))
  ("MTEXT" "CACEM - TESTI" ((content . "44") (position . ((x . -219.135845229145) (y . 125.573179889231))) (height . 0.140146525954482) (rotation . 0.0)))
  ("MTEXT" "CACEM - TESTI" ((content . "44") (position . ((x . -219.546996611524) (y . 125.338707297736))) (height . 0.093431017302988) (rotation . 0.0)))
  ("MTEXT" "CACEM - TESTI" ((content . "44") (position . ((x . -218.724693846767) (y . 125.338707297736))) (height . 0.093431017302988) (rotation . 0.0)))
  ("MTEXT" "CACEM - TESTI" ((content . "44") (position . ((x . -218.376718213558) (y . 122.327797815135))) (height . 0.140146525954482) (rotation . 0.0)))
  ("MTEXT" "CACEM - TESTI" ((content . "44") (position . ((x . -217.675985583785) (y . 122.327797815135))) (height . 0.140146525954482) (rotation . 0.0)))
  ("MTEXT" "CACEM - TESTI" ((content . "44") (position . ((x . -219.135845229146) (y . 125.832810871893))) (height . 0.140146525954482) (rotation . 0.0)))
  ("TEXT" "CACEM - TESTI" ((content . "20") (position . ((x . -216.757945884519) (y . 50))) (height . 0.140146525954482) (rotation . 90)))
  ("MTEXT" "CACEM - TESTI" ((content . "44") (position . ((x . -216.804661393171) (y . 124.237328070765))) (height . 0.140146525954482) (rotation . 0.0)))
  ("MTEXT" "CACEM - TESTI" ((content . "44") (position . ((x . 7) (y . 122.636260897466))) (height . 0.0851390145173479) (rotation . 0.0)))
  ("MTEXT" "CACEM - TESTI" ((content . "44") (position . ((x . -220.084389695891) (y . 122.636260897466))) (height . 0.0851390145173479) (rotation . 0.0)))
  ("MTEXT" "CACEM - TESTI" ((content . "44") (position . ((x . 7) (y . 122.636260897466))) (height . 0.0851390145173479) (rotation . 0.0)))
  ("MTEXT" "CACEM - TESTI" ((content . "44") (position . ((x . -218.189719084174) (y . 122.636260897466))) (height . 0.0851390145173479) (rotation . 0.0)))
  ("MTEXT" "CACEM - TESTI" ((content . "44") (position . ((x . -219.934625804759) (y . 122.636260897466))) (height . 0.0851390145173479) (rotation . 0.0)))
  ("MTEXT" "CACEM - TESTI" ((content . "44") (position . ((x . -219.794847316641) (y . 122.636260897466))) (height . 0.0851390145173479) (rotation . 0.0)))
  ("MTEXT" "CACEM - TESTI" ((content . "44") (position . ((x . -219.641089950467) (y . 122.636260897466))) (height . 0.0851390145173479) (rotation . 0.0)))
  ("MTEXT" "CACEM - TESTI" ((content . "44") (position . ((x . -219.205778870537) (y . 122.636260897466))) (height . 0.0851390145173479) (rotation . 0.0)))
  ("MTEXT" "CACEM - TESTI" ((content . "44") (position . ((x . -219.064001929489) (y . 122.636260897466))) (height . 0.0851390145173479) (rotation . 0.0)))
  ("MTEXT" "CACEM - TESTI" ((content . "44") (position . ((x . -218.624697374516) (y . 122.636260897466))) (height . 0.0851390145173479) (rotation . 0.0)))
  ("MTEXT" "CACEM - TESTI" ((content . "44") (position . ((x . -218.478926958426) (y . 122.636260897466))) (height . 0.0851390145173479) (rotation . 0.0)))
  ("MTEXT" "CACEM - TESTI" ((content . "44") (position . ((x . -218.331159804815) (y . 122.636260897466))) (height . 0.0851390145173479) (rotation . 0.0)))
  ("MTEXT" "CACEM - TESTI" ((content . "44") (position . ((x . -217.144499330765) (y . 122.849292653646))) (height . 0.0851390145173479) (rotation . 0.0)))
  ("MTEXT" "CACEM - TESTI" ((content . "44") (position . ((x . -217.144499330765) (y . 122.990966344839))) (height . 0.0851390145173479) (rotation . 0.0)))
  ("MTEXT" "CACEM - TESTI" ((content . "44") (position . ((x . -207.553691802831) (y . 130.417024320127))) (height . 0.12) (rotation . 0.0)))
  ("MTEXT" "CACEM - TESTI" ((content . "44") (position . ((x . -207.403124562441) (y . 130.78514934249))) (height . 0.12) (rotation . 0.0)))
  ("MTEXT" "CACEM - TESTI" ((content . "44") (position . ((x . -207.934100575544) (y . 130.903436626627))) (height . 0.12) (rotation . 0.0)))
  ("MTEXT" "CACEM - TESTI" ((content . "44") (position . ((x . -209.944090834478) (y . 130.995336464483))) (height . 0.12) (rotation . 0.0)))
  ("MTEXT" "CACEM - TESTI" ((content . "44") (position . ((x . -209.419478174215) (y . 130.819111617301))) (height . 0.12) (rotation . 0.0)))
  ("TEXT" "CACEM - TESTI" ((content . "POSIZIONAMENTO GANCI") (position . ((x . -214.877579439941) (y . 126.752378701103))) (height . 0.286616550460317) (rotation . 0.0)))
  ("TEXT" "CACEM - TESTI" ((content . "INTEGRAZIONE APPOGGIO TEGOLO") (position . ((x . -223.156396544176) (y . 133.067050678342))) (height . 0.08) (rotation . 0.0)))
  ("TEXT" "CACEM - TESTI" ((content . "INTEGRAZIONE APPOGGIO TEGOLO") (position . ((x . -223.156396544176) (y . 132.433885156214))) (height . 0.08) (rotation . 0.0)))
  ("MTEXT" "CACEM - TESTI" ((content . "44") (position . ((x . -216.043541155131) (y . 128.248710787235))) (height . 0.12) (rotation . 0.0)))
  ("MTEXT" "CACEM - TESTI" ((content . "44") (position . ((x . -215.887292853512) (y . 128.612570218204))) (height . 0.12) (rotation . 0.0)))
  ("MTEXT" "CACEM - TESTI" ((content . "44") (position . ((x . -215.522719482519) (y . 128.822638626543))) (height . 0.12) (rotation . 0.0)))
  ("TEXT" "CACEM - TESTI" ((content . "TNL7") (position . ((x . -208.630894941465) (y . 137.845837694421))) (height . 1.8) (rotation . 0.0)))
  ("TEXT" "CACEM - TESTI" ((content . "0") (position . ((x . -220.976789267929) (y . 121.556397992055))) (height . 0.12) (rotation . 0.0)))
  ("TEXT" "CACEM - TESTI" ((content . "0") (position . ((x . -220.306078117737) (y . 121.556397992055))) (height . 0.12) (rotation . 0.0)))
  ("TEXT" "CACEM - TESTI" ((content . "11") (position . ((x . -225.473253396131) (y . 135.537369652295))) (height . 0.194843527834025) (rotation . 0.0)))
  ("TEXT" "CACEM - TESTI" ((content . "11") (position . ((x . -224.855914231456) (y . 135.537369652295))) (height . 0.194843527834025) (rotation . 0.0)))
  ("TEXT" "CACEM - TESTI" ((content . "11") (position . ((x . -212.777933648603) (y . 128.222950545106))) (height . 0.12) (rotation . 90)))
  ("TEXT" "CACEM - TESTI" ((content . "11") (position . ((x . -212.614465251323) (y . 128.21866483082))) (height . 0.12) (rotation . 90)))
  ("TEXT" "CACEM - TESTI" ((content . "3") (position . ((x . -217.975880149237) (y . 134.48669011325))) (height . 0.158635849251743) (rotation . 0.0)))
  ("TEXT" "CACEM - TESTI" ((content . "(rete â") (position . ((x . -212.205790883075) (y . 133.087695996098))) (height . 0.15) (rotation . 0.0)))
  ("TEXT" "CACEM - TESTI" ((content . "pos. 5a/6a   /   pos.11") (position . ((x . -214.305906434201) (y . 133.087695996098))) (height . 0.15) (rotation . 0.0)))
  ("TEXT" "CACEM-TESTI" ((content . "COMMITTENTE :") (position . ((x . -209.840704015118) (y . 122.264456372684))) (height . 0.100264894676322) (rotation . 0.0)))
  ("TEXT" "CACEM-TESTI" ((content . "SEDE") (position . ((x . -209.808563933359) (y . 121.909232669882))) (height . 0.0870354988509739) (rotation . 0.0)))
  ("TEXT" "CACEM-TESTI" ((content . "CANTIERE") (position . ((x . -209.839698371031) (y . 121.590953929655))) (height . 0.0870354988509739) (rotation . 0.0)))
  ("TEXT" "CACEM - TESTI" ((content . "0") (position . ((x . -208.842090163907) (y . 122.27215535498))) (height . 0.193885037929316) (rotation . 0.0)))
  ("TEXT" "CACEM-TESTI" ((content . "1071") (position . ((x . -209.199962021227) (y . 121.573532903467))) (height . 0.183113646933218) (rotation . 0.0)))
  ("TEXT" "CACEM-TESTI" ((content . "1071") (position . ((x . -209.376476735377) (y . 121.911127746851))) (height . 0.183113646933218) (rotation . 0.0)))
  ("TEXT" "CACEM-TESTI" ((content . "DATA:") (position . ((x . -209.865766415761) (y . 123.310685716712))) (height . 0.0870354988509739) (rotation . 0.0)))
  ("TEXT" "CACEM - TESTI" ((content . "3") (position . ((x . -215.397053966091) (y . 135.186030002467))) (height . 0.139566613331816) (rotation . 0.0)))
  ("TEXT" "CACEM - TESTI" ((content . "GANCIO DEHA") (position . ((x . -209.809571561947) (y . 135.772841976763))) (height . 0.08) (rotation . 0.0)))
  ("TEXT" "CACEM-TESTI" ((content . "EDIFICIO") (position . ((x . -205.742607914132) (y . 123.074555496802))) (height . 0.372125482768313) (rotation . 0.0)))
  ("TEXT" "41" ((content . "11") (position . ((x . -225.860330647799) (y . 129.357303859403))) (height . 0.233812233400829) (rotation . 0.0)))
  ("TEXT" "CACEM - TESTI" ((content . "11") (position . ((x . -225.860330647799) (y . 128.307493467004))) (height . 0.233812233400829) (rotation . 0.0)))
  ("TEXT" "CACEM - TESTI" ((content . "11") (position . ((x . 41) (y . 127.541460932234))) (height . 0.233812233400829) (rotation . 0.0)))
  ("TEXT" "CACEM - TESTI" ((content . "11") (position . ((x . -225.473635709131) (y . 133.497657111876))) (height . 0.194843527834025) (rotation . 0.0)))
  ("TEXT" "CACEM - TESTI" ((content . "11") (position . ((x . -225.473635709131) (y . 132.591111886583))) (height . 0.194843527834025) (rotation . 0.0)))
  ("TEXT" "CACEM - TESTI" ((content . "11") (position . ((x . -225.319638346518) (y . 129.336683843689))) (height . 0.194843527834025) (rotation . 0.0)))
  ("TEXT" "CACEM - TESTI" ((content . "11") (position . ((x . -225.319638346518) (y . 128.284154908289))) (height . 0.194843527834025) (rotation . 0.0)))
  ("TEXT" "CACEM - TESTI" ((content . "11") (position . ((x . -225.394328365521) (y . 127.518122373518))) (height . 0.194843527834025) (rotation . 0.0)))
  ("TEXT" "CACEM - TESTI" ((content . "90") (position . ((x . -211.561726673692) (y . 125.140073046))) (height . 0.0322070608812399) (rotation . 0.0)))
  ("TEXT" "CACEM-TESTI" ((content . "1B-1C-2B-2C") (position . ((x . -206.115422663599) (y . 122.627194718694))) (height . 0.348867640095294) (rotation . 0.0)))
  ("TEXT" "CACEM - TESTI" ((content . "S") (position . ((x . -204.271640112854) (y . 125.017880460647))) (height . 0.125592350434323) (rotation . 0.0)))
  ("TEXT" "CACEM - TESTI" ((content . "2 cm") (position . ((x . -204.352747489923) (y . 124.65058951864))) (height . 0.125592350434323) (rotation . 0.0)))
  ("MTEXT" "CACEM - TESTI" ((content . "44") (position . ((x . -212.298582713067) (y . 130.468572943096))) (height . 0.12) (rotation . 7)))
  ("TEXT" "CACEM - TESTI" ((content . "11") (position . ((x . -209.227933648603) (y . 128.222950545106))) (height . 0.12) (rotation . 90)))
  ("TEXT" "CACEM - TESTI" ((content . "11") (position . ((x . -209.064465251323) (y . 128.21866483082))) (height . 0.12) (rotation . 90)))
  ("TEXT" "CACEM - TESTI" ((content . "superiore") (position . ((x . -223.192514188258) (y . 136.320973265768))) (height . 0.0974217639170123) (rotation . 0.0)))
  ("TEXT" "CACEM - TESTI" ((content . "inferiori") (position . ((x . -223.156396585844) (y . 135.421608267381))) (height . 0.0974217639170123) (rotation . 0.0)))
  ("TEXT" "CACEM - TESTI" ((content . "ferri di parete") (position . ((x . -223.156396340527) (y . 134.280344752131))) (height . 0.0974217639170123) (rotation . 0.0)))
  ("TEXT" "CACEM - TESTI" ((content . "11") (position . ((x . -212.777933648603) (y . 136.247004260775))) (height . 0.12) (rotation . 90)))
  ("TEXT" "CACEM - TESTI" ((content . "11") (position . ((x . -212.614465251323) (y . 136.242718546489))) (height . 0.12) (rotation . 90)))
  ("MTEXT" "CACEM - TESTI" ((content . "44") (position . ((x . -212.765047549706) (y . 133.761454390896))) (height . 0.15) (rotation . 0.0)))
  ("TEXT" "CACEM - TESTI" ((content . "11") (position . ((x . -209.227933648604) (y . 136.247004260774))) (height . 0.12) (rotation . 90)))
  ("TEXT" "CACEM - TESTI" ((content . "11") (position . ((x . -209.064465251324) (y . 136.242718546489))) (height . 0.12) (rotation . 90)))
  ("TEXT" "CACEM - TESTI" ((content . "28/02/2023") (position . ((x . -207.174624567568) (y . 122.925567982202))) (height . 0.0768283635677804) (rotation . 0.0)))
  ("TEXT" "CACEM-TESTI" ((content . "ESECUTIVO DI PRODUZIONE  FEBBRAIO 2023") (position . ((x . -209.37764653514) (y . 123.324966392441))) (height . 0.0995686106855142) (rotation . 0.0)))
  ("MTEXT" "CACEM - TESTI" ((content . "44") (position . ((x . -214.848582713018) (y . 130.468572943096))) (height . 0.12) (rotation . 7)))
  ("MTEXT" "CACEM - TESTI" ((content . "44") (position . ((x . -209.748582713066) (y . 130.468572943096))) (height . 0.12) (rotation . 7)))
)))
    T)
  T)

(defun entity-type (ent) (if (listp ent) (car ent) NIL))
(defun entity-layer (ent) (if (and (listp ent) (>= (length ent) 2)) (cadr ent) NIL))
(defun entity-geometry (ent) (if (and (listp ent) (>= (length ent) 3)) (caddr ent) NIL))
(defun safe-assoc (key alist)
  (if (listp alist)
      (assoc key alist)
      NIL))
(defun safe-cdr (x)
  (if (listp x)
      (cdr x)
      NIL))
(defun safe-car (x)
  (if (listp x)
      (car x)
      NIL))
(defun geometry-get (geom key)
  (if (listp geom)
      (safe-cdr (safe-assoc key geom))
      NIL))
(defun as-2d-point (v)
  (cond
    ((and (listp v) (>= (length v) 2)) v)
    ((and (listp v) (safe-assoc 'x v) (safe-assoc 'y v))
      (list (safe-cdr (safe-assoc 'x v)) (safe-cdr (safe-assoc 'y v))))
    ((numberp v) (list v 0.0))
    ((and (listp v) (= (length v) 1)) (list (safe-car v) 0.0))
    (T (list 0.0 0.0))))
(defun point-x (p)
  (let ((pp (as-2d-point p)))
    (if (and (listp pp) (> (length pp) 0)) (car pp) 0.0)))
(defun point-y (p)
  (let ((pp (as-2d-point p)))
    (if (and (listp pp) (> (length pp) 1)) (cadr pp) 0.0)))
(defun test-first-contour-entity ()
  (if (and (listp *tnl7-contour*) (> (length *tnl7-contour*) 0))
      (let* ((ent (car *tnl7-contour*))
             (et (entity-type ent))
             (ly (entity-layer ent))
             (geom (entity-geometry ent)))
        (and (= et "LWPOLYLINE")
             (= ly "CACEM - LINEE SCHEDA")
             (listp geom)))
    NIL)
)

(defun create-layer (name / layer-exists)
  (setq layer-exists (tblsearch "LAYER" name))
  (if (null layer-exists)
      (progn
        (command "_.LAYER" "_MAKE" name "")
        T)
    )
  T
)

(defun ensure-layers ()
  (mapcar 'create-layer '(
    "CACEM - LINEE SCHEDA"
    "CACEM - ARMATURA"
    "CACEM - GANCI DEHA"
    "CACEM - HALFEN"
    "CACEM - TREFOLI"
    "CACEM-QUOTE"
    "CACEM - TESTI"
    "CACEM-TESTI"
    "CACEM - PIASTRA POSIZIONE Y"
    "CACEM-TRAVE U CANALE"
    "CACEM - TABELLE"))
)

(defun create-line-entity (p1 p2 layer)
  (let* ((p1p (as-2d-point p1))
         (p2p (as-2d-point p2)))
    (entmake (list
      (cons 0 "LINE")
      (cons 8 layer)
      (cons 10 (point-x p1p)) (cons 20 (point-y p1p)) (cons 30 0.0)
      (cons 11 (point-x p2p)) (cons 21 (point-y p2p)) (cons 31 0.0))))
)

(defun create-circle-entity (center radius layer)
  (let* ((cp (as-2d-point center)))
    (entmake (list
      (cons 0 "CIRCLE")
      (cons 8 layer)
      (cons 10 (point-x cp)) (cons 20 (point-y cp)) (cons 30 0.0)
      (cons 40 radius)))))

(defun create-arc-entity (center radius start-angle end-angle layer)
  (let* ((cp (as-2d-point center)))
    (entmake (list
      (cons 0 "ARC")
      (cons 8 layer)
      (cons 10 (point-x cp)) (cons 20 (point-y cp)) (cons 30 0.0)
      (cons 40 radius)
      (cons 50 start-angle)
      (cons 51 end-angle)))))

(defun create-lwpolyline-entity (pts bulges closed layer)
  (entmake (append
    (list
      (cons 0 "LWPOLYLINE")
      (cons 8 layer)
      (cons 90 (length pts))
      (cons 70 (if closed 1 0)))
    (apply 'append
      (mapcar '(lambda (pt bulge)
                (let* ((pp (as-2d-point pt)))
                  (list (cons 10 (point-x pp)) (cons 20 (point-y pp)) (cons 42 bulge))))
              pts bulges)))
)
)

(defun create-text-entity (content pos height rotation layer)
  (let* ((pp (as-2d-point pos)))
    (entmake (list
      (cons 0 "TEXT")
      (cons 8 layer)
      (cons 10 (point-x pp)) (cons 20 (point-y pp)) (cons 30 0.0)
      (cons 40 height)
      (cons 50 rotation)
      (cons 1 content)))))

(defun create-mtext-entity (content pos height layer)
  (let* ((pp (as-2d-point pos)))
    (entmake (list
      (cons 0 "MTEXT")
      (cons 8 layer)
      (cons 10 (point-x pp)) (cons 20 (point-y pp)) (cons 30 0.0)
      (cons 41 height)
      (cons 1 content)))))

(defun create-dimension-visual (point1 point2 text-pos label layer)
  (let* ((p1p (as-2d-point point1))
         (p2p (as-2d-point point2))
         (tpp (as-2d-point text-pos)))
    (create-line-entity p1p p2p layer)
    (create-line-entity (list (point-x p1p) (+ (point-y p1p) 0.5)) (list (point-x p2p) (+ (point-y p2p) 0.5)) layer)
    (create-text-entity label tpp 0.12 0.0 layer)))

(defun draw-primitive (ent)
  (let* ((ent-type (entity-type ent))
         (ent-layer (entity-layer ent))
         (geom (entity-geometry ent)))
    (cond
      ((= ent-type "LINE")
        (create-line-entity
          (list (cdr (assoc 'x (geometry-get geom 'start))) (cdr (assoc 'y (geometry-get geom 'start))))
          (list (cdr (assoc 'x (geometry-get geom 'end))) (cdr (assoc 'y (geometry-get geom 'end))))
          ent-layer))
      ((= ent-type "ARC")
        (create-arc-entity
          (list (cdr (assoc 'x (geometry-get geom 'center))) (cdr (assoc 'y (geometry-get geom 'center))))
          (geometry-get geom 'radius)
          (geometry-get geom 'start_angle)
          (geometry-get geom 'end_angle)
          ent-layer))
      ((= ent-type "CIRCLE")
        (create-circle-entity
          (list (cdr (assoc 'x (geometry-get geom 'center))) (cdr (assoc 'y (geometry-get geom 'center))))
          (geometry-get geom 'radius)
          ent-layer))
      ((= ent-type "LWPOLYLINE")
        (create-lwpolyline-entity
          (mapcar '(lambda (v) (list (cdr (assoc 'x v)) (cdr (assoc 'y v)))) (geometry-get geom 'vertices))
          (if (geometry-get geom 'bulges) (geometry-get geom 'bulges) (mapcar '(lambda (v) 0.0) (geometry-get geom 'vertices)))
          (geometry-get geom 'closed)
          ent-layer))
      ((= ent-type "TEXT")
        (create-text-entity
          (geometry-get geom 'content)
          (list (cdr (assoc 'x (geometry-get geom 'position))) (cdr (assoc 'y (geometry-get geom 'position))))
          (geometry-get geom 'height)
          (geometry-get geom 'rotation)
          ent-layer))
      ((= ent-type "MTEXT")
        (create-mtext-entity
          (geometry-get geom 'content)
          (list (cdr (assoc 'x (geometry-get geom 'position))) (cdr (assoc 'y (geometry-get geom 'position))))
          (geometry-get geom 'height)
          ent-layer))
      ((= ent-type "DIMENSION")
        (create-dimension-visual
          (list (cdr (assoc 'x (geometry-get geom 'point1))) (cdr (assoc 'y (geometry-get geom 'point1))))
          (list (cdr (assoc 'x (geometry-get geom 'point2))) (cdr (assoc 'y (geometry-get geom 'point2))))
          (list (cdr (assoc 'x (geometry-get geom 'text_position))) (cdr (assoc 'y (geometry-get geom 'text_position))))
          (rtos (geometry-get geom 'value) 2 1)
          ent-layer))
      (T NIL))
  )
)

(defun draw-section (items)
  (foreach item items
    (draw-primitive item))
)

(defun create-holes ()
  (foreach item *tnl7-holes*
    (foreach primitive (geometry-get (entity-geometry item) 'world_geometry)
      (draw-primitive primitive))))

(defun create-reinforcement ()
  (draw-section *tnl7-reinforcement*))

(defun create-halfens ()
  (draw-section *tnl7-halfens*))

(defun create-deha ()
  (draw-section *tnl7-deha*))

(defun create-strands ()
  (draw-section *tnl7-strands*))

(defun create-mask ()
  (draw-section *tnl7-mask*))

(defun create-dimensions ()
  (foreach item *tnl7-dimensions*
    (if (= (entity-type item) "DIMENSION")
      (create-dimension-visual
        (list (cdr (assoc 'x (geometry-get (entity-geometry item) 'point1))) (cdr (assoc 'y (geometry-get (entity-geometry item) 'point1))))
        (list (cdr (assoc 'x (geometry-get (entity-geometry item) 'point2))) (cdr (assoc 'y (geometry-get (entity-geometry item) 'point2))))
        (list (cdr (assoc 'x (geometry-get (entity-geometry item) 'text_position))) (cdr (assoc 'y (geometry-get (entity-geometry item) 'text_position))))
        (rtos (geometry-get (entity-geometry item) 'value) 2 1)
        (entity-layer item)
      )
    )
  )
)

(defun create-text-elements ()
  (foreach item *tnl7-texts*
    (if (and (= (entity-type item) "TEXT")
             (/= (strcase (geometry-get (entity-geometry item) 'content)) "TNL7"))
      (create-text-entity
        (geometry-get (entity-geometry item) 'content)
        (list (cdr (assoc 'x (geometry-get (entity-geometry item) 'position))) (cdr (assoc 'y (geometry-get (entity-geometry item) 'position))))
        (geometry-get (entity-geometry item) 'height)
        (geometry-get (entity-geometry item) 'rotation)
        (entity-layer item)
      )
    )
  )
)

(defun create-tnl-label (n)
  (setq *tnl7-label* (strcat "TNL" (itoa n)))
  (create-text-entity *tnl7-label* (list -208.630894941465 137.845837694421) 1.8 0.0 "CACEM - TESTI")
  (create-text-entity *tnl7-label* (list -208.842090163907 122.272155354980) 0.193885037929316 0.0 "CACEM - TESTI")
)

(defun c:TNLMASTER ()
  (tnl7-ensure-data)
  (setq *tnl7-input* (getstring T "Numero TNL <7>: "))
  (if (= *tnl7-input* "")
      (setq *tnl7-input* "7"))
  (setq *tnl7-number* (atoi *tnl7-input*))
  (if (zerop *tnl7-number*)
      (setq *tnl7-number* 7))
  (setq *tnl7-label* (strcat "TNL" (itoa *tnl7-number*)))
  (command "_.UNDO" "_BEGIN")
  (ensure-layers)
  (draw-section *tnl7-contour*)
  (create-holes)
  (create-reinforcement)
  (create-halfens)
  (create-deha)
  (create-strands)
  (create-mask)
  (create-dimensions)
  (create-text-elements)
  (create-tnl-label *tnl7-number*)
  (command "_.UNDO" "_END")
  (princ (strcat "TNL7 recreated with label: " *tnl7-label*))
  (princ)
)

(princ "TNL7_MASTER loaded. Type TNLMASTER to generate the drawing.")
(princ)
